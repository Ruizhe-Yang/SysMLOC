package Atoms{
	doc /* This package defines a keyword (atom) for classifiers with
	 * exactly one instance and are disjoint from any others
	 * marked with this keyword.
	 */
	private import Metaobjects::Metaobject;
	classifier Atom;
	metaclass < atom > AtomMetadata :> Metaobject{
		baseType = Atom meta KerML::Classifier{
		}
	}
}
