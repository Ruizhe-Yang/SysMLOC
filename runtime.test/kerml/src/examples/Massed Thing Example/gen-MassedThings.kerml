private import ScalarValues :: *;
package MassedThings{
	public class MassedThing{
		public name : String{
		}
		public mass : Real = 0{
		}
	}
	public assoc MassedThingAssembly{
		public end [ 0 .. 1 ] feature assembly : MassedThing{
		}
		public end [ 0 .. * ] feature parts : MassedThing{
		}
	}
}
