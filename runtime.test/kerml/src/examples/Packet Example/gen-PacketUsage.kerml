private import Packets :: *;
private import ScalarValues::Real;
package 'Packet Usage'{
	feature packet1 : 'Thermal Data Packet'{
	}
	feature packet2 : 'Thermal Data Packet'{
	}
	feature packet3 : 'Thermal Data Packet'{
		feature 'special data field' :>> 'packet data field'{
			feature :>> 'user data field'{
				feature 'special data' : Real{
				}
			}
		}
	}
}
