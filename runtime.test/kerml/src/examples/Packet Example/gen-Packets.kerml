private import ScalarValues :: *;
private import Time::DateTime;
package Packets{
	feature 'packet header'{
	}
	feature 'packet data field'{
		feature 'packet secondary header' :>> 'packet header'{
		}
		feature 'user data field'{
		}
	}
	class 'Data Packet'{
		feature 'packet primary header' :>> 'packet header'{
			feature 'packet version number' : Integer{
			}
			feature 'packet identification' : String{
			}
			feature 'packet data length' : Integer{
			}
		}
		feature :>> 'packet data field'{
		}
	}
	class 'Thermal Data Packet' :> 'Data Packet'{
		feature 'packet data field' :>> Packets::'packet data field'{
			feature 'packet secondary header' :>> 'packet header'{
				feature 'packet timestamp' : DateTime{
				}
				feature 'telemetry packet type' : String{
				}
			}
			feature 'user data field' :>> Packets::'packet data field'::'user data field'{
				feature timestamp : DateTime{
				}
				feature temperature : Real{
				}
			}
		}
	}
}
