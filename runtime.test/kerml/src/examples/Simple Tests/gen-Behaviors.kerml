package Behaviors{
	behavior A{
		in x{
		}
		out y = b.y1{
		}
		composite step b : B{
			in x1 = A::x{
			}
		}
	}
	behavior B :> A{
		in x1{
		}
		out var y1{
		}
	}
	class C{
		var z = A().y{
		}
		step a : A;
		step b : B;
		binding z = a.y;
		flow from a.y to b.x1;
	}
	abstract flow msg of C;
}
