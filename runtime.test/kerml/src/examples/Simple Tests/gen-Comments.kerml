/* AAA */
//a lexical comment ("note") is not a part of model
package Comments{
	// inside package
	/*
*AAA
 * BBB*/
	/*
    *
    *
    * AAA  ***   
    *BBB
    								*/
	/*
 *       AAAA
 *       BBBB           */
	/* AAAA
 
 
  * BBBB
 *
 * CCCC
 */
	locale "en_US" /*
 * AAAA
 * BBBB
 *    CCC DDD    
 */
	/* comment inside a package */
	comment cmt /* Named Comment */
	comment cmt_cmt about cmt /* Other Comment about Comment */
	class C{
		doc locale "en_US" /* Documentation on Class C */
		/* Comment in Class C */
		comment about Comments /* Comment about Package */
	}
	/* abc */
	class A{
		doc < a > /* Documentation comment on A*/
		comment about a locale "en_US" /* Comment about documenation with ID 'a' */
	}
}
