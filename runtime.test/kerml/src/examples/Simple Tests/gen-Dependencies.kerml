package Dependencies{
	package System{
		package 'Application Layer';
		package 'Service Layer';
		package 'Data Layer';
	}
	public import System :: *;
	dependency Use from 'Application Layer' to 'Service Layer';
	dependency 'Service Layer' to 'Data Layer';
	feature x{
	}
	feature y{
	}
	feature z{
	}
	dependency z to x , y{
		feature e{
		}
	}
}
