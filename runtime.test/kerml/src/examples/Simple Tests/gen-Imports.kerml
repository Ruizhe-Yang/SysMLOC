package Imports{
	package P{
		class A;
		class B;
		class C;
	}
	package Q{
		class A;
		class D{
			class E;
		}
		package Q1{
			class D;
			class E;
			private package Q1a{
				class G;
			}
		}
		package Q2{
			class F;
		}
	}
	package R{
		public import Q :: *;
	}
	package S{
		public import P :: *;
		public import Q :: **;
		class X :> A;
		class Y :> D;
		class Z :> F;
	}
	package S1{
		public import P :: *;
		public import R :: *;
		class X :> A;
	}
}
