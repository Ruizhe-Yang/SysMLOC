package Scoping{
	package P1{
		class A{
			feature f{
			}
		}
		package P2{
			class A{
				feature g{
				}
			}
			package P3{
				class B :> A{
					feature :>> g{
					}
				}
			}
		}
		package Objects{
			class Object{
				feature test1{
				}
			}
		}
		package '$'{
			class Objects{
				class Object{
					feature test2{
					}
				}
			}
		}
		package P4{
			class C :> Objects::Object{
				feature :>> test1{
				}
			}
			class D :> '$'::Objects::Object{
				feature :>> test2{
				}
			}
			class E :> '$'::Objects::Object{
				feature :>> subobjects{
				}
			}
		}
	}
}
