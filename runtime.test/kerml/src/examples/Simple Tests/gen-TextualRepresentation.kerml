package TextualRepresentation{
	private import ScalarValues::Real;
	class C{
		feature x : Real{
		}
		inv x_constraint{
			rep inOCL language "ocl" /* self.x > 0.0 */
		}
	}
	behavior setX{
		in c : C{
		}
		in newX : Real{
		}
		language "alf" /* c.x = newX;
	         * WriteLine("Set new x");
	         */
	}
}
