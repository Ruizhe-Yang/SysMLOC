package TimeVaryingFeaturesEnhanced{
	private import ExtendedOccurrences :: *;
	class CC1 :> ExtendedOccurrence{
		var feature x{
		}
		//member feature x featured by CC1_snapshots {
		//    member feature CC1_snapshots :>> ExtendedOccurrences::ExtendedOccurrence::snapshots featured by CC1;
		//}
		// portions are not variable
		portion :>> startShot{
			var feature :>> x = 0{
			}
			//member feature :>> CC1::x featured by CC1_startShot_snapshots = 0 {
			//    member feature CC1_startShot_snapshots :>> CC1_snapshots featured by CC1::startShot;
			//}
		}
		portion t :> timeSlices{
			var feature y{
			}
			//member feature y featured by CC1_t_snapshots {
			//    member feature CC1_t_snapshots :>> ExtendedOccurrences::ExtendedOccurrence::snapshots featured by CC1::t;
			//}
			portion :>> startShot{
				var feature :>> x = 0{
				}
				//member feature :>> CC1::x featured by CC1_t_startShot_snapshots = 0 {
				//    member feature CC1_t_startShot_snapshots :>> CC1_snapshots featured by CC1::t::startShot;
				//}
				var feature :>> y = 1{
				}
				//member feature :>> CC1::t::y featured by CC1_t_startShot_snapshots = 1 {
				//    member feature CC1_t_startShot_snapshots :>> CC1_t_snapshots featured by CC1::t::startShot;
				//}
			}
			portion t1 :> timeSlices{
				portion :>> startShot{
					var feature :>> x = 2{
					}
					//member feature :>> CC1::x featured by CC1_t_t1_startShot_snapshots = 2 {
					//    member feature CC1_t_t1_startShot_snapshots :>> CC1_snapshots featured by CC1::t::t1::startShot;
					//}
					var feature :>> y = 3{
					}
					//member feature :>> CC1::t::y featured by CC1_t_t1_startShot_snapshots = 3 {
					//    member feature CC1_t_t1_startShot_snapshots :>> CC1_t_snapshots featured by CC1::t::t1::startShot;
					//}
				}
			}
		}
	}
	private import ScalarValues::Boolean;
	private import ScalarValues::Real;
	class Car :> ExtendedOccurrence{
		var feature driver [ 0 .. 1 ] : Person{
		}
		//member feature driver : Person [0..1] featured by Car_snapshots {
		//    member feature Car_snapshots :>> ExtendedOccurrences::ExtendedOccurrence::snapshots featured by Car;
		//}
		var feature speed [ 1 ] : Real{
		}
		//member feature speed : Real [1] featured by Car_snapshots {
		//    member feature Car_snapshots :>> ExtendedOccurrences::ExtendedOccurrence::snapshots featured by Car;
		//}
		// bind the current speed to the current speed of the current driver
		// var binding driver.speed = speed;
		//member connector : Links::SelfLink featured by Car_snapshots {
		//	:>> that : Car_snapshots;
		//	end feature :>> thisThing references that.driver.while{interval = Car_snapshots::self}.speed;
		//	end feature :>> thisThing references that.driver.at{timeslices = Car_snapshots::self.moment}.speed;
		//	end feature :>> sameThing references that.speed;
		//    member feature Car_snapshots :>> ExtendedOccurrences::ExtendedOccurrence::snapshots featured by Car;
		//}
		portion operated [ 0 .. * ] :> timeSlices{
			var feature [ 1 ] :>> driver{
			}
			//member feature :>> Car::driver [1] featured by Car_operated_snapshots {
			//    member feature Car_operated_snapshots :>> Car_snapshots featured by Car::operated;
			// var feature :>> isLicensed = true;
			//    member feature isLicensed1 :>> Person::isLicensed featured by Car_operated_driver_snapshots = true {
			//        member feature Car_operated_driver_snapshots :>> Person_snapshots featured by Car::operated::driver;
			//    }
			//}
			//portion :>> snapshots {
			//    public import operated;
			//}
		}
		var feature engine [ 1 ]{
		}
		//member feature engine [1] featured by Car_snapshots {
		//    member feature Car_snapshots :>> ExtendedOccurrences::ExtendedOccurrence::snapshots featured by Car;
		//}       
		var feature transmission [ 1 ]{
		}
		//member feature transmission [1] featured by Car_snapshots {
		//    member feature Car_snapshots :>> ExtendedOccurrences::ExtendedOccurrence::snapshots featured by Car;
		//}       
		var connector drive from engine to transmission;
		//member connector drive featured by Car_snapshots from engine to transmission {
		//    member feature Car_snapshots :>> ExtendedOccurrences::ExtendedOccurrence::snapshots :> engine::Car_snapshots, transmission::Car_snapshots featured by Car;
		//}
		portion inOperable [ 0 .. 1 ] :> timeSlices{
		}
		// successions are not variable
		succession first operated then inOperable;
	}
	class Person :> ExtendedOccurrence{
		var feature isLicensed [ 0 .. 1 ] : Boolean{
		}
		//member feature isLicensed : Boolean[0..1] featured by Person_snapshots {
		//    member feature Person_snapshots :>> ExtendedOccurrences::ExtendedOccurrence::snapshots featured by Person;
		//}
		var feature speed [ 1 ] : Real{
		}
		//member feature speed : Real[1] featured by Person_snapshots {
		//    member feature Person_snapshots :>> ExtendedOccurrences::ExtendedOccurrence::snapshots featured by Person;
		//}
	}
	struct Car1 :> ExtendedObject{
		// May or may not be a life
		var feature driver [ 0 .. 1 ] : Person{
		}
		//member feature driver : Person [0..1] featured by Car_snapshots {
		//    member feature Car_snapshots :>> ExtendedOccurrences::ExtendedOccurrence::snapshots featured by Car1;
		//}
		// :>> timeSlices : Car;  <-- Don't do this!
		portion :>> startShot{
			// Not a kind of Car!
			var feature [ 0 ] :>> driver{
			}
			//member feature :>> driver : Person [0] featured by Car_startShot_snapshots {
			//    member feature Car_startShot_snapshots :>> Car_snapshots featured by Car1::startShot;
			//}
		}
		succession first startShot then driven;
		portion driven :> timeSlices{
			var feature [ 1 ] :>> driver{
			}
			// No conflict with multiplicity! (driven just can't be startshot)
			//member feature :>> driver : Person [1] featured by Car_driven_snapshots {
			//    member feature Car_driven_snapshots :>> Car_snapshots featured by Car1::driven;
			//}
		}
	}
}
