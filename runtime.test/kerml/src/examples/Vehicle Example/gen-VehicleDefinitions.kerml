package VehicleDefinitions{
	doc /*
	 * Example vehicle definitions model.
	 */
	/* BLOCKS */
	class Vehicle;
	class Transmission;
	class AxleAssembly;
	class Axle;
	class Wheel;
	class Lugbolt{
		tighteningTorque [ 1 ] : ScalarValues::Real{
		}
	}
	/* INTERFACE BLOCKS */
	class DriveIF{
		in driveTorque : ScalarValues::Real{
		}
	}
	class AxleMountIF{
		out transferredTorque : ScalarValues::Real{
		}
	}
	class WheelHubIF{
		in appliedTorque : ScalarValues::Real{
		}
	}
	/* ASSOCIATION BLOCKS */
	assoc Mounting{
		doc /*
		 *  mounting a Wheel to an Axle.
		 */
		end axleMount : AxleMountIF{
		}
		end hub : WheelHubIF{
		}
	}
}
