// /** Mandatory Services and Systems */
library package AHFCoreLib{
	private import AHFProfileLib :: *;
	private import ScalarValues :: *;
	private import AHFProfileMetadata :: *;
	#service port def ServiceDiscovery{
		// The functionalities as Requests (Operations) cannot be defined yet
		// We could consider using flows to designate the functionalities
	}
	#service port def ServiceDiscoveryDD : ServiceDiscovery;
	#service port def Authorisation{
		attribute publickey : String;
		// just as examples
	}
	#service port def AuthorisationDD : Authorisation;
	#clouddd ArrowheadCore{
		// /** Design Level */
		// First the system definitions (SysD) of core systems
		#system service_registry{
			#service serviceDiscovery : ServiceDiscovery;
		}
		#system authorization{
			#service authorisation : Authorisation;
			attribute protocol : String = "HTTP";
		}
		#system orchestrationDesign;
		// just indicated for now
		// /** Design Description level */		
		#systemdd service_registry_DD :> service_registry{
			#servicedd : ServiceDiscoveryDD :>> serviceDiscovery{
				#idd serviceDiscovery_HTTP;
				// nested port for HTTP protocol
				// here we refer the functionalities like operation Register etc.
				#idd serviceDiscovery_MQTT;
				// nested port for MQTT protocol
			}
		}
		#systemdd authorization_DD :> authorization{
			#servicedd :>> authorisation{
				#idd authorisation_HTTP;
				// nested port for HTTP protocol
				#idd authorisation_MQTT;
				// nested port for MQTT protocol
			}
			action Echo_behavior :> ServiceMethod;
		}
	}
}
