package AHFNorway{
	doc /* This is the Norwegian use-case for Arrowhead Framework */
	// The use-case is for Productive4.0 and Arrowhead Tools
	// The system is taken from a chemical factory
	// This is focusing on the monitoring of products when delivered
	private import AHFProfileLib :: *;
	private import AHFProfileMetadata :: *;
	private import AHFCoreLib :: **;
	private import ScalarValues :: *;
	#service def APISService{
		doc /* Service design */
		attribute :>> serviceDefinition = "APISPullService";
		attribute :>> intrfce_protocol = "{
			JSON
		}
		";
		attribute :>> serviceURL = "pull";
	}
	#servicedd port def APIS_DD : APISService{
		doc /* Service design description with nested protocol-specific ports */
		#idd port APIS_HTTP{
			// the asynch implementation of synchronous remote calls
			out cll : CallGiveItems;
			in retrn : ResultGiveItems;
		}
		#idd port APIS_MQTT{
			// GetAllItems functionality
			out pub : Publish;
			out retall : Return_AllItems;
			in subscr : Subscribe;
		}
	}
	// Asynchronous signals
	attribute def Publish{
		nametopic : String;
	}
	attribute def Subscribe{
		nametopic : String;
	}
	attribute def Return_AllItems{
		itms : String;
	}
	attribute def Subscribe_giveItems{
		itms : String;
	}
	attribute def Return_Ack{
		ack : Boolean;
	}
	// Signals for implementing the remote procedure call by asynch signals
	attribute def CallGiveItems{
		itms : String;
	}
	attribute def ResultGiveItems{
		ack : Boolean;
	}
	#clouddd AHFNorway_LocalCloudDD :> ArrowheadCore{
		#systemdd TellUConsumer{
			#servicedd serviceDiscovery : ~ServiceDiscoveryDD;
			// communicating with ServiceRegistry
			#servicedd apisp : APIS_DD;
			attribute :>> systemname = "UngerApisClient";
			attribute :>> address = "Unger_network_ip";
			attribute :>> portno = 0;
			// We want an operation call to GiveItems, and actually sending the payload
			// Call apisp::APIS_HTTP::giveItems(in allitems: String = "All the items", out ackback:Boolean);
			state TellUbehavior{
				entry send new CallGiveItems("All the items") via apisp.APIS_HTTP;
				then Wait;
				// Here do whatever about the result rs.ret 
				state Wait;
				accept rs : ResultGiveItems then Wait;
			}
		}
		#systemdd APISProducer{
			#servicedd serviceDiscovery : ~ServiceDiscoveryDD;
			// communicating with ServiceRegistry
			#servicedd tellu : ~APIS_DD;
			// providing the APISService
			#servicedd apisc : APIS_DD;
			// talking to APISConsumer
			:>> systemname = "PrediktorApisServer";
			:>> address = "Prediktor_network_ip";
			:>> portno = 6565;
			attribute x : Boolean;
			action giveItems :> ServiceMethod{
				in itms : String;
				out ack : Boolean;
				/* Forward itms and return an ack */
				first start;
				then send new Return_AllItems(itms) via apisc.APIS_MQTT;
				success = true;
				bind ack = success;
			}
			state APISPbehavior{
				entry send new Publish("Return_AllItems") via apisc.APIS_MQTT;
				then WaitOnData;
				state WaitOnData;
				accept cl : CallGiveItems via tellu.APIS_HTTP do action {
					first start;
					then action giveItems{
						in itms = cl.itms;
						out ack = x;
					}
				then send new ResultGiveItems(x) via tellu.APIS_HTTP;
				}
				then WaitOnData;
			}
		}
		#systemdd APISConsumer{
			#servicedd serviceDiscovery : ~ServiceDiscovery;
			// communicating with ServiceRegistry
			#servicedd apisp : ~APIS_DD;
			:>> systemname = "TellUClient";
			:>> address = "Prediktor_network_ip";
			:>> portno = 1;
			// Now sending signal to the remote behavior through the port functionality
			state MQTT_APISP{
				entry send new Subscribe("Return_AllItems") via apisp.APIS_MQTT;
				then Idle;
				state Idle;
				// Get the stuff and do something with them
				accept Return_AllItems via apisp.APIS_MQTT then Idle;
			}
		}
		part MQTTServer{
			port getTopic : ~APIS_DD;
			port giveTopic : APIS_DD;
			state Serve{
				entry;
				then Publ;
				state Publ;
				// store information about who will provide "Publish::nametopic"
				accept pub : Publish via getTopic.APIS_MQTT then Subsr;
				state Subsr;
				// store information about who want to receive "Subscribe::nametopic"
				accept Subscribe via giveTopic.APIS_MQTT then Idle;
				state Idle;
				accept retrnall : Return_AllItems via getTopic.APIS_MQTT do send retrnall via giveTopic.APIS_MQTT then Idle;
			}
		}
		connect APISProducer.apisc to MQTTServer.getTopic;
		connect MQTTServer.giveTopic to APISConsumer.apisp;
		connect TellUConsumer.apisp to APISProducer.tellu;
		// Then we need to connect the application systems to the mandatory systems
		connect APISProducer.serviceDiscovery to service_registry.serviceDiscovery;
		connect TellUConsumer.serviceDiscovery to service_registry.serviceDiscovery;
		connect APISConsumer.serviceDiscovery to service_registry.serviceDiscovery;
		// Same procedure for the other mandatory services
	}
}
