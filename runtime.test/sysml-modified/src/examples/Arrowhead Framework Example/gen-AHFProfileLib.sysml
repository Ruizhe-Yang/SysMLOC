library package AHFProfileLib{
	// Systems and Services and their functionalities
	private import ScalarValues :: *;
	// Design level
	port def SD{
		doc /* Service definition */
		attribute serviceDefinition : String;
		attribute serviceURL : String;
		attribute intrfce_protocol : String;
		// which may be "REST" or "MQTT" etc.		 
	}
	part def SysLocalCloudsDesign{
		doc /* System of Systems Definition */
		// System of Local Clouds 
		part locclouds [ 1 .. * ] : LocalCloudDesign;
	}
	part system_of_systems : SysLocalCloudsDD;
	// defining a top level usage
	part def LocalCloudDesign{
		doc /* Local Cloud definition */
		part systems [ 1 .. * ] : SysD;
	}
	part def SysD{
		doc /* System definitions */
		port services [ 1 .. * ] : SD;
		attribute systemname : String;
		attribute address : String;
		attribute portno : Integer;
	}
	// Design Description level
	port def IDD : SD{
		doc /* Interface Design Description of services */
		attribute encoding_kind : String;
	}
	port def SDDD : SD{
		doc /* Service Definition Design Description */
		port idds [ * ] : IDD;
		// nested protocol-specific services
	}
	part def SysLocalCloudsDD : SysLocalCloudsDesign{
		doc /* System of Systems Detailed Description */
		part [ 1 .. * ] : LocalCloudDD :>> locclouds;
		// the descriptions
	}
	part def LocalCloudDD : LocalCloudDesign{
		part [ 1 .. * ] : SysDD :>> systems;
	}
	part def SysDD : SysD{
		doc /* System Detailed Description */
		port : SDDD :>> services;
		action ServiceMethod [ 1 .. * ];
		//means general behaviors
	}
}
library package AHFProfileMetadata{
	private import Metaobjects::SemanticMetadata;
	private import AHFProfileLib :: *;
	port global_sd : SD;
	metadata def < service > SDMetadata : SemanticMetadata{
		// :>> baseType = system_of_systems.locclouds.systems.services meta SysML::PortUsage;
		// :>> baseType = SysD::services meta SysML::PortUsage;
		:>> baseType default global_sd meta SysML::PortUsage;
	}
	metadata def < sos > SysLocalCloudsMetadata : SemanticMetadata{
		:>> baseType = system_of_systems meta SysML::PartUsage;
	}
	metadata def < cloud > LocalCloudsMetadata : SemanticMetadata{
		:>> baseType default system_of_systems::locclouds meta SysML::PartUsage;
	}
	metadata def < system > SysDMetadata : SemanticMetadata{
		:>> baseType default system_of_systems::locclouds::systems meta SysML::PartUsage;
		// :>> baseType default LocalCloudDesign::systems meta SysML::PartUsage;
	}
	metadata def < idd > IDDMetadata : SDMetadata{
		// :>> baseType = system_of_systems.locclouds.systems.services.idd meta SysML::PortUsage;
		:>> baseType = SDDD::idds meta SysML::PortUsage;
		// :>> global_sddd.idd;
	}
	port global_sddd : SDDD;
	metadata def < servicedd > SDDDMetadata : SDMetadata{
		// :>> baseType = system_of_systems.locclouds.systems.services meta SysML::PortUsage;
		:>> baseType = global_sddd meta SysML::PortUsage;
	}
	metadata def < clouddd > LocalCloudsDDMetadata : LocalCloudsMetadata{
		:>> baseType = system_of_systems::locclouds meta SysML::PartUsage;
	}
	part global_clouddd : LocalCloudDD;
	part global_systemsdd : SysDD;
	metadata def < systemdd > SysDDMetadata : SysDMetadata{
		// :>> baseType = system_of_systems.locclouds.systems meta SysML::PartUsage;
		//:>> baseType = LocalCloudDD::systems meta SysML::PartUsage;
		:>> baseType = global_systemsdd meta SysML::PartUsage;
	}
}
