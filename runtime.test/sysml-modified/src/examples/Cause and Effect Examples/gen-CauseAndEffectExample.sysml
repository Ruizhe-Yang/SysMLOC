package CauseAndEffectExample{
	private import CauseAndEffect :: *;
	part def Causer1;
	part def Causer2;
	part def Effected1;
	part def Effected2;
	#multicausation connection def MultiCauseEffect{
		end #cause cause1 : Causer1;
		end #cause cause2 : Causer2;
		end #effect effect1 : Effected1;
		end #effect effect2 : Effected2;
	}
	part causer1 : Causer1;
	part causer2 : Causer2;
	part effected1 : Effected1;
	part effected2 : Effected2;
	#multicausation connection : MultiCauseEffect connect ( cause1 ::> causer1 , cause2 ::> causer2 , effect1 ::> effected1 , effect2 ::> effected2 );
	#multicausation connect ( cause1 ::> causer1 , cause2 ::> causer2 , effect1 ::> effected1 , effect2 ::> effected2 );
	occurrence a;
	item b;
	part c;
	action d;
	#multicausation connection{
		end #cause ::> a;
		end #cause ::> b;
		end #effect ::> c;
		end #effect ::> d;
	}
	#cause causeA ::> a;
	#cause causeB ::> b;
	#effect effectC ::> c;
	#effect effectD ::> d;
	#multicausation connect ( causeA , causeB , effectC , effectD );
	#causation connect a to c;
	#causation connect b to d{
		metadata CausationMetadata{
			isNecessary = true;
			probability = 0.1;
		}
	}
}
