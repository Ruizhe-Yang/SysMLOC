package MedicalDeviceFailure{
	private import CauseAndEffect :: *;
	part medicalDevice{
		part battery{
			event occurrence depleted;
			event occurrence cannotBeCharged;
		}
		event occurrence deviceFails;
		ref patient{
			event occurrence therapyDelayed;
		}
		#multicausation connection{
			end #cause ::> battery.depleted;
			end #cause ::> battery.cannotBeCharged;
			end #effect ::> deviceFails;
		}
		#causation connect deviceFails to patient.therapyDelayed;
	}
}
