package Comments{
	doc /* Documentation Comment */
	doc /* Documentation about Package */
	comment cmt /* Named Comment */
	comment cmt_cmt about cmt /* Comment about Comment */
	comment about C /* Documention Comment on Part Def */
	part def C{
		doc /* Documentation in Part Def */
		/* Comment in Part Def */
		comment about Comments /* Comment about Package */
	}
}
