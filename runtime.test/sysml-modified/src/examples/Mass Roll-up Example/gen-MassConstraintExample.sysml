package MassConstraintExample{
	private import ISQ :: *;
	private import SI :: *;
	private import NumericalFunctions :: *;
	part def Engine{
		attribute m :> mass;
	}
	part def Transmission{
		attribute m :> mass;
	}
	part def Vehicle1{
		attribute m : MassValue = eng.m + trans.m;
		part eng : Engine{
			attribute : MassValue :>> m;
		}
		part trans : Transmission{
			attribute : MassValue :>> m;
		}
	}
	part def Vehicle2{
		assert constraint{
			m == eng.m + trans.m
		}
		attribute m : MassValue;
		part eng : Engine{
			attribute : MassValue :>> m;
		}
		part trans : Transmission{
			attribute : MassValue :>> m;
		}
	}
	constraint def MassConstraint3{
		in totalMass : MassValue;
		in partMasses [ 0 .. * ] : MassValue;
		totalMass == sum(partMasses)
	}
	part def Vehicle3{
		assert constraint massConstraint : MassConstraint3{
			in totalMass = m;
			in partMasses = (eng.m, trans.m);
		}
		attribute m : MassValue;
		part eng{
			attribute m : MassValue;
		}
		part trans{
			attribute m : MassValue;
		}
	}
	constraint def MassConstraint4{
		in totalMass : MassValue;
		in partMasses [ 0 .. * ] : MassValue;
	}
	constraint mc : MassConstraint4{
		in totalMass : MassValue;
		in partMasses [ 0 .. * ] : MassValue;
		totalMass == sum(partMasses)
	}
	part def Vehicle4{
		assert mc{
			in totalMass = m;
			in partMasses = (eng.m, trans.m);
		}
		attribute m : MassValue;
		part eng : Engine{
			attribute : MassValue :>> m;
		}
		part trans : Transmission{
			attribute : MassValue :>> m;
		}
	}
	constraint def MassLimit{
		in mass : MassValue;
		in maxMass : MassValue;
		mass <= maxMass
	}
	part def Vehicle5{
		assert constraint ml : MassLimit{
			in mass = m;
			in maxMass = 2500 [kg];
		}
		attribute m : MassValue = eng.m + trans.m;
		part eng : Engine{
			attribute : MassValue :>> m;
		}
		part trans : Transmission{
			attribute : MassValue :>> m;
		}
	}
}
