package MassRollup{
	private import NumericalFunctions :: *;
	part def MassedThing{
		attribute mass :> ISQ::mass;
		attribute totalMass :> ISQ::mass;
	}
	part simpleThing : MassedThing{
		attribute :>> totalMass = mass;
	}
	part compositeThing : MassedThing{
		part subcomponents [ * ] : MassedThing;
		attribute :>> totalMass default mass + sum(subcomponents.totalMass);
	}
	part filteredMassThing :> compositeThing{
		abstract attribute minMass :> ISQ::mass;
		attribute :>> totalMass = mass + sum(subcomponents.totalMass.?{
			in p :> ISQ::mass;
			p > minMass
		}
		);
	}
}
