package 'Packet Usage'{
	public import Packets :: *;
	private import ScalarValues::Real;
	part packet1 : 'Thermal Data Packet';
	part packet2 : 'Thermal Data Packet';
	part packet3 : 'Thermal Data Packet'{
		attribute 'special data field' :>> 'packet data field'{
			attribute :>> 'user data field'{
				attribute 'special data' : Real;
			}
		}
	}
}
