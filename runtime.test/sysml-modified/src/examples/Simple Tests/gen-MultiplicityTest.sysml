package MultiplicityTest{
	part def P;
	attribute n : ScalarValues::Integer = 5;
	part a [ 1 ];
	part b [ 0 .. 2 ] : P;
	part c [ 2 .. * ] : P;
	part d [ * ];
	part e [ n ];
	part f [ n .. * ];
	part g [ 1 .. n ];
	attribute def A{
		attribute i : ScalarValues::Integer;
		attribute x [ i ] : A;
	}
}
