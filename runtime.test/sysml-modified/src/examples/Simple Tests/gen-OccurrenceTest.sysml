package OccurrenceTest{
	occurrence def Occ{
		attribute a;
		ref occurrence occ1 : Occ;
		occurrence occ2 : Occ;
		item x;
		part y;
		individual snapshot s : Ind;
		timeslice t;
	}
	occurrence occ : Occ{
		occurrence o1 : Occ;
		ref occurrence o2 : Occ;
		item z;
	}
	individual occurrence def Ind{
		snapshot s2;
		timeslice t2;
	}
	individual occurrence ind : Ind : Occ{
		snapshot s3;
		individual timeslice t3 :> ind;
		individual snapshot s4 : Ind;
	}
	occurrence o1{
		occurrence o2;
	}
}
