// State Space Representation cart example
package CartSample{
	private import StateSpaceRepresentation :: *;
	part def Cart{
		attribute mass :> ISQ::mass;
		attribute def CartInput : Input{
			attribute force :> ISQ::force;
		}
		attribute def CartOutput : Output{
			attribute velocity :> ISQ::speed;
		}
		attribute def CartState : StateSpace{
			attribute velocity :> ISQ::speed;
		}
		attribute def CartStateDerivative : StateDerivative{
			ref : CartState :>> stateSpace;
			attribute accel :> ISQ::acceleration;
		}
	}
	part def Pusher{
		attribute def PusherOutput : Output{
			attribute force :> ISQ::force;
		}
	}
	part context{
		part cart : Cart{
			action cartBehavior : ContinuousStateSpaceDynamics{
				in input : CartInput;
				out output : CartOutput;
				: CartState :>> stateSpace;
				calc :>> getDerivative{
					in input : CartInput;
					in stateSpace : CartState;
					new CartStateDerivative(input.force / mass)
				}
				calc :>> getOutput{
					in : CartState :>> stateSpace;
					new CartOutput(stateSpace.velocity)
				}
			}
		}
		part pusher : Pusher{
			attribute pusherForce :> ISQ::force;
			action pusherBehavior : ContinuousStateSpaceDynamics{
				in input;
				out output : PusherOutput;
				calc :>> getOutput{
					new PusherOutput(pusherForce)
				}
			}
		}
		flow pusher.pusherBehavior.output to cart.cartBehavior.input;
	}
}
