package TimeVaryingAttribute{
	private import SI::s;
	item def PwrCmd{
		attribute pwrLevel : ScalarValues::Integer;
	}
	part def Transport2{
		private import Time :: *;
		attribute startTime = TimeOf(start);
		attribute elapseTime :> ISQ::duration;
		attribute :>> localClock.currentTime = startTime + elapseTime;
		out item pwrCmd : PwrCmd;
		// Lifetime conditions
		timeslice :>> portionOfLife{
			snapshot :>> start{
				:>> elapseTime = 0 [s];
				:>> pwrCmd.pwrLevel = 0;
			}
			snapshot :>> done{
				:>> elapseTime = 2 [s];
				:>> pwrCmd.pwrLevel = 1;
			}
		}
		//     Alternative:
		//       // initial conditions
		//       :>> portionOfLife.start : C {
		//           :>> elapseTime = 0 [s];
		//           :>> pwrCmd.pwrLevel = 0;
		//       }
		timeslice transportPeriod{
			snapshot :>> start{
				:>> elapseTime = 1 [s];
			}
			snapshot :>> done{
				:>> elapseTime = 1.5 [s];
			}
			:>> pwrCmd.pwrLevel = 2*elapseTime.num;
		}
		//      Alternative:
		//        // final conditions
		//        :>> portionOfLife.done {
		//            :>> elapseTime = 2 [s];
		//            :>> pwrCmd.pwrLevel = 1;
		//        }
	}
}
