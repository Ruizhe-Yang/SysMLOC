package 'Interface Decomposition Example'{
	port def SpigotBank;
	port def Spigot;
	port def Faucet;
	port def FaucetInlet;
	interface def WaterDelivery{
		end [ 1 ] port suppliedBy : SpigotBank{
			port hot : Spigot;
			port cold : Spigot;
		}
		end [ 1 .. * ] port deliveredTo : Faucet{
			port hot : FaucetInlet;
			port cold : FaucetInlet;
		}
		connect suppliedBy.hot to deliveredTo.hot;
		connect suppliedBy.cold to deliveredTo.cold;
	}
}
