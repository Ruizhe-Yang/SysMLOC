package 'Binding Connectors Example-1'{
	private import 'Port Example' :: *;
	part def Vehicle;
	part def FuelPump;
	part def FuelTank;
	part vehicle : Vehicle{
		part tank : FuelTankAssembly{
			port :>> fuelTankPort{
				out item :>> fuelSupply;
				in item :>> fuelReturn;
			}
			bind fuelTankPort.fuelSupply = pump.pumpOut;
			bind fuelTankPort.fuelReturn = tank.fuelIn;
			part pump : FuelPump{
				out item pumpOut : Fuel;
				in item pumpIn : Fuel;
			}
			part tank : FuelTank{
				out item fuelOut : Fuel;
				in item fuelIn : Fuel;
			}
		}
	}
}
