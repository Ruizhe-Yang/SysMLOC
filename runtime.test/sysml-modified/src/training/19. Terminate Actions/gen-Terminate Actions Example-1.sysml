package 'Terminate Actions Example-1'{
	private import ScalarValues::Boolean;
	action monitorCriticalActivity;
	action criticalActivity;
	action waitForTimeOut;
	action def MonitoredActivity{
		first start;
		then fork;
		then performCriticalActivity;
		then waitForTimeOut;
		action performCriticalActivity{
			perform monitorCriticalActivity;
			perform criticalActivity;
			then terminate;
		}
		then stop;
		action waitForTimeOut;
		then stop;
		action stop terminate;
	}
}
