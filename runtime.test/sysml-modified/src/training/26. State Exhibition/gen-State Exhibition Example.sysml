package 'State Exhibition Example'{
	private import 'Transition Actions' :: *;
	part vehicle : Vehicle{
		part vehicleController : VehicleController;
		exhibit vehicleStates{
			in operatingVehicle = vehicle;
			in controller = vehicleController;
		}
	}
}
