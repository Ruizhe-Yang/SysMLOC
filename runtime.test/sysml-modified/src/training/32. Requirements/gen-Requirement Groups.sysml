package 'Requirement Groups'{
	private import 'Requirement Definitions' :: *;
	private import 'Requirement Usages' :: *;
	part def Engine{
		port clutchPort : ClutchPort;
		perform action generateTorque : GenerateTorque;
	}
	requirement vehicleSpecification{
		doc /* Overall vehicle requirements group */
		subject vehicle : Vehicle;
		require fullVehicleMassLimit;
		require emptyVehicleMassLimit;
	}
	requirement engineSpecification{
		doc /* Engine power requirements group */
		subject engine : Engine;
		requirement drivePowerInterface : DrivePowerInterface{
			subject = engine.clutchPort;
		}
		requirement torqueGeneration : TorqueGeneration{
			subject = engine.generateTorque;
		}
	}
}
