package 'Allocation Definition Example'{
	package LogicalModel{
		action def ProvidePower;
		action def GenerateTorque;
		part def LogicalElement;
		part def TorqueGenerator : LogicalElement;
		action providePower : ProvidePower{
			action generateTorque : GenerateTorque;
		}
		part torqueGenerator : TorqueGenerator{
			perform providePower.generateTorque;
		}
	}
	package PhysicalModel{
		private import LogicalModel :: *;
		part def PhysicalElement;
		part def PowerTrain : PhysicalElement;
		part powerTrain : PowerTrain{
			part engine{
				perform providePower.generateTorque;
			}
		}
		allocation def LogicalToPhysical{
			end logical : LogicalElement;
			end physical : PhysicalElement;
		}
		allocation torqueGenAlloc : LogicalToPhysical allocate torqueGenerator to powerTrain;
	}
}
