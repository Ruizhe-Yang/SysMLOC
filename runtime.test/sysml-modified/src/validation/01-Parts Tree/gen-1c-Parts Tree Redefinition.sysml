package '1c-Parts Tree Redefinition'{
	private import SI::kg;
	package Definitions{
		part def Vehicle{
			attribute mass :> ISQ::mass;
		}
		part def AxleAssembly;
		part def Axle{
			attribute mass :> ISQ::mass;
		}
		part def FrontAxle : Axle{
			attribute steeringAngle : ScalarValues::Real;
		}
		part def Wheel;
	}
	package Usages{
		private import Definitions :: *;
		part vehicle1 : Vehicle{
			attribute mass :>> Vehicle::mass default 1750 [kg]{
				doc /*
			 * The mass attribute is redefined to give it a default value.
			 */
			}
			part frontAxleAssembly : AxleAssembly{
				part frontAxle : Axle;
				part frontWheel [ 2 ] ordered : Wheel;
			}
			part rearAxleAssembly : AxleAssembly{
				part rearAxle : Axle;
				part rearWheel [ 2 ] ordered : Wheel;
			}
		}
		part vehicle1_c1 :> vehicle1{
			/*
			 * 'vehicle1_c1' is a specialization of 'vehicle1' (technically 
			 * a subset). It inherits all the parts of 'vehicle1' and
			 * only needs to specify additional or redefined parts.
			 */
			attribute mass :>> vehicle1::mass = 2000 [kg]{
				/*
				 * The mass is further redefined to override the default value
				 * with a bound value for 'vehicle_c1'.
				 */
			}
			part frontAxleAssembly_c1 :>> frontAxleAssembly{
				part frontAxle_c1 : FrontAxle :>> frontAxle{
					/*
					 * 'frontAxle_c1' redefines 'frontAxleAssembly'::'frontAxle'
					 * to give it a new name and the specialized type
					 * 'FrontAxle'.
					 */
				}
				/*
				 * 'frontWheel' is inherited from 'vehicle1'::'frontAxleAssembly',
				 * allowing it to be used in the following part declarations.
				 */
				part frontWheel_1 :> frontWheel = frontWheel#(1);
				part frontWheel_2 :> frontWheel = frontWheel#(2);
			}
			part rearAxleAssembly_c1 :>> rearAxleAssembly{
				part rearAxle_c1 :>> rearAxle{
					/*
					 * 'rearAxle_c1' redefines 'rearAxleAssembly'::'rearAxle'
					 * to give it a new name. It inherits the type 'Axle'
					 * from the redefined part.
					 */
				}
				part rearWheel_1 :> rearWheel = rearWheel#(1);
				part rearWheel_2 :> rearWheel = rearWheel#(2);
			}
		}
	}
}
