package '1d-Parts Tree with Reference'{
	package Definitions{
		part def Vehicle;
		part def Trailer;
		part def TrailerHitch;
		part def HitchBall;
		part def TrailerCoupler;
	}
	package Usages{
		private import Definitions :: *;
		part vehicle_trailer_system{
			part vehicle1_c1 : Vehicle{
				ref hitchBall : HitchBall{
					/*
					 * 'vehicle1_c1'::'hitchBall' is a reference property that
					 * references a hitch ball that is not part of this vehicle. 
					 * If 'vehicle1_c1' is removed or destroyed, this does not
					 * effect the hitchBall referenced here.
					 */
				}
			}
			bind vehicle1_c1.hitchBall = trailerHitch.hitchBall{
				/*
				 * This is a binding connector between the 'hitchBall' in 'vehicle1_c1'
				 * and the 'hitchBall' in 'trailerHitch'.
				 */
			}
			part trailerHitch : TrailerHitch{
				part hitchBall : HitchBall;
				part trailerCoupler : TrailerCoupler;
			}
			part trailer1 : Trailer{
				ref trailerCoupler : TrailerCoupler = trailerHitch.trailerCoupler{
					/*
					 * This is a shorthand for a binding connector between the
					 * 'trailerCoupler' here and the 'trailerCoupler' in 'trailerHitch'.
					 * The binding connector is now contained within the 'trailer1'
					 * part, though, rather than being at the system level. 
					 */
				}
			}
		}
	}
}
