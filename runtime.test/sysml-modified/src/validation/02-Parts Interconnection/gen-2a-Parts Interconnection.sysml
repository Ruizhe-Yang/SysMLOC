package '2a-Parts Interconnection'{
	public import Definitions :: *;
	public import Usages :: *;
	package Definitions{
		// Port Definitions
		port def FuelCmdPort;
		port def DrivePwrPort;
		port def ClutchPort;
		port def ShaftPort_a;
		port def ShaftPort_b;
		port def ShaftPort_c;
		port def ShaftPort_d;
		port def DiffPort;
		port def AxlePort;
		port def AxleToWheelPort;
		port def WheelToAxlePort;
		port def WheelToRoadPort;
		port def VehicleToRoadPort{
			/*
			 * A port definition can have nested ports.
			 */
			port wheelToRoadPort [ 2 ] : WheelToRoadPort;
		}
		// Blocks
		part def VehicleA{
			port fuelCmdPort : FuelCmdPort;
			port vehicleToRoadPort : VehicleToRoadPort;
		}
		part def AxleAssembly;
		part def RearAxleAssembly : AxleAssembly{
			port shaftPort_d : ShaftPort_d;
		}
		part def Axle;
		part def RearAxle : Axle;
		part def HalfAxle{
			port axleToDiffPort : AxlePort;
			port axleToWheelPort : AxleToWheelPort;
		}
		part def Engine{
			port fuelCmdPort : FuelCmdPort;
			port drivePwrPort : DrivePwrPort;
		}
		part def Transmission{
			port clutchPort : ClutchPort;
			port shaftPort_a : ShaftPort_a;
		}
		part def Driveshaft{
			port shaftPort_b : ShaftPort_b;
			port shaftPort_c : ShaftPort_c;
		}
		part def Differential{
			/*
			 * Ports do not have to be defined on part defs.
			 * They can be added directly to their usages.
			 */
		}
		part def Wheel;
		// Interface Definitions
		interface def EngineToTransmissionInterface{
			/*
			 * The ends of an interface definition are always ports.
			 */
			end drivePwrPort : DrivePwrPort;
			end clutchPort : ClutchPort;
		}
		interface def DriveshaftInterface{
			end shaftPort_a : ShaftPort_a;
			end shaftPort_d : ShaftPort_d;
			ref driveshaft : Driveshaft{
				/*
				 * 'driveshaft' is a reference to the driveshaft that will
				 * act as the "interface medium" for this interface.
				 */
			}
			connect shaftPort_a to driveshaft.shaftPort_b{
				/*
				 * The two ends of 'DriveShaftInterface' are always connected
				 * via the referenced 'driveshaft'.
				 */
			}
			connect driveshaft.shaftPort_c to shaftPort_d;
		}
	}
	package Usages{
		part vehicle1_c1 : VehicleA{
			bind fuelCmdPort = engine.fuelCmdPort;
			part engine : Engine;
			interface : EngineToTransmissionInterface connect engine.drivePwrPort to transmission.clutchPort{
				/*
				 * A usage of an interface definition connects two ports relative to 
				 * a containing context.
				 */
			}
			part transmission : Transmission;
			part driveshaft : Driveshaft{
				/*
				 * This 'driveshaft' is the part of 'vehicle1_c1' that will act as the
				 * interface medium in the following 'DriveshaftInterface' usage.
				 */
			}
			interface : DriveshaftInterface connect transmission.shaftPort_a to rearAxleAssembly.shaftPort_d{
				ref :>> driveshaft = vehicle1_c1.driveshaft{
					/*
						 * The reference property from 'DriveshaftInterface' is redefined
						 * in order to bind it to the appropriate part of 'vehicle1_c1'.
						 */
				}
			}
			part rearAxleAssembly : RearAxleAssembly{
				bind shaftPort_d = differential.shaftPort_d;
				part differential : Differential{
					port shaftPort_d : ShaftPort_d{
						/*
						 * If the part def has no ports, then they can be defined directly in
						 * a usage of the part def.
						 */
					}
					port leftDiffPort : DiffPort;
					port rightDiffPort : DiffPort;
				}
				interface differential.leftDiffPort to rearAxle.leftHalfAxle.axleToDiffPort{
					/*
					 * A connection can be to a port that is arbitrarily deeply nested, on either end. 
					 */
				}
				interface differential.rightDiffPort to rearAxle.rightHalfAxle.axleToDiffPort;
				part rearAxle : RearAxle{
					part leftHalfAxle : HalfAxle;
					part rightHalfAxle : HalfAxle;
				}
				connect rearAxle.leftHalfAxle.axleToWheelPort to leftWheel.wheelToAxlePort;
				connect rearAxle.rightHalfAxle.axleToWheelPort to rightWheel.wheelToAxlePort;
				part rearWheel [ 2 ] ordered : Wheel;
				/* The two rear wheels of 'rearAxleAssembly' must be given
				 * their own names in order to be referenced in connections.
				 * 
				 * (":>" is a shorthand here for "subsets".)
				 */
				part leftWheel :> rearWheel = rearWheel#(1){
					port wheelToAxlePort : WheelToAxlePort;
					port wheelToRoadPort : WheelToRoadPort;
				}
				part rightWheel :> rearWheel = rearWheel#(2){
					port wheelToAxlePort : WheelToAxlePort;
					port wheelToRoadPort : WheelToRoadPort;
				}
			}
			bind rearAxleAssembly.leftWheel.wheelToRoadPort = vehicleToRoadPort.leftWheelToRoadPort;
			bind rearAxleAssembly.rightWheel.wheelToRoadPort = vehicleToRoadPort.rightWheelToRoadPort;
			port vehicleToRoadPort :>> VehicleA::vehicleToRoadPort{
				port leftWheelToRoadPort :> wheelToRoadPort = wheelToRoadPort#(1);
				port rightWheelToRoadPort :> wheelToRoadPort = wheelToRoadPort#(2);
			}
		}
	}
}
