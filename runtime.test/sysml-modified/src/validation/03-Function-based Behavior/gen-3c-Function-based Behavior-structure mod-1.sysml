package '3c-Function-based Behavior-structure mod-1'{
	part def Vehicle;
	part def VehicleFrame;
	part def HitchBall;
	part def TrailerCoupler;
	part def Trailer;
	part def TrailerFrame;
	connection def TrailerHitch{
		end hitch : HitchBall;
		end coupler : TrailerCoupler;
	}
	part 'vehicle-trailer system'{
		part vehicle : Vehicle{
			part vehicleFrame : VehicleFrame{
				part hitch : HitchBall;
			}
		}
		connection trailerHitch [ 0 .. 1 ] : TrailerHitch connect vehicle.vehicleFrame.hitch to trailer.trailerFrame.coupler;
		part trailer : Trailer{
			part trailerFrame : TrailerFrame{
				part coupler : TrailerCoupler;
			}
		}
		action{
			// Create a link and assign it as the TrailerHitch connection.
			// Link participants are determined from inherited ends.
			action 'connect trailer to vehicle' assign 'vehicle-trailer system'.trailerHitch := new TrailerHitch();
			// Destroy the link object.
			then action 'destroy connection of trailer to vehicle' : OccurrenceFunctions::destroy{
				inout occ = 'vehicle-trailer system'.trailerHitch;
			}
			// Remove the link from the TrailerHitch connection.
			then action 'disconnect trailer from vehicle' assign 'vehicle-trailer system'.trailerHitch := null;
		}
	}
}
