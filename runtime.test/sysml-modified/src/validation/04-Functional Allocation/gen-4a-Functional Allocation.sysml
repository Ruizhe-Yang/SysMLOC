package '4a-Functional Allocation'{
	private import '2a-Parts Interconnection' :: *;
	private import '3a-Function-based Behavior-1' :: *;
	private import '3a-Function-based Behavior-1'::'provide power' :: *;
	part vehicle1_c1_functional_allocation :> vehicle1_c1{
		// Note: The definitions of the port types in '2a-Parts Interconnection' do not include 
		// flow properties.
		port :>> fuelCmdPort{
			in fuelCmd : FuelCmd;
		}
		perform 'provide power'{
			doc /*
		 * This allocates the action '3a-Function-based Behavior-1'::'provide power' as an enacted 
		 * performance of 'vehicle_c1_functional_allocation'.
		 */
			// This assigns the fuelCmdPort to provide the input to 'provide power'.
			in fuelCmd = fuelCmdPort.fuelCmd;
		}
		part :>> engine{
			port :>> fuelCmdPort{
				in fuelCmd : FuelCmd;
			}
			perform 'provide power'.'generate torque'{
				/*
				 *  This allocates one of the sub-steps of 'provide power' to a sub-part of vehicle_c1. 
				 */
				in fuelCmd = fuelCmdPort.fuelCmd;
				out engineTorque = drivePwrPort.engineTorque;
			}
			port :>> drivePwrPort{
				out engineTorque : Torque;
			}
		}
		part :>> transmission{
			port :>> clutchPort{
				in attribute engineTorque : Torque;
			}
			perform 'provide power'.'amplify torque'{
				in engineTorque = clutchPort.engineTorque;
				out transmissionTorque = shaftPort_a.transmissionTorque;
			}
			port :>> shaftPort_a{
				out transmissionTorque : Torque;
			}
		}
		part :>> driveshaft{
			port :>> shaftPort_b{
				in transmissionTorque : Torque;
			}
			perform 'provide power'.'transfer torque'{
				in transmissionTorque = shaftPort_b.transmissionTorque;
				out driveshaftTorque = shaftPort_c.driveshaftTorque;
			}
			port :>> shaftPort_c{
				out driveshaftTorque : Torque;
			}
		}
		part :>> rearAxleAssembly{
			port :>> shaftPort_d{
				in driveshaftTorque : Torque;
			}
			perform 'provide power'.'distribute torque'{
				in driveshaftTorque = shaftPort_d.driveshaftTorque;
				out wheelTorque1 = rearAxle.leftHalfAxle.axleToWheelPort.wheelTorque;
				out wheelTorque2 = rearAxle.rightHalfAxle.axleToWheelPort.wheelTorque;
			}
			part :>> rearAxle{
				part :>> leftHalfAxle{
					port :>> axleToWheelPort{
						out wheelTorque : Torque;
					}
				}
				part :>> rightHalfAxle{
					port :>> axleToWheelPort{
						out wheelTorque : Torque;
					}
				}
			}
		}
	}
}
