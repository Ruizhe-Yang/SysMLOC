package '8-Requirements'{
	private import ScalarValues::Real;
	private import ISQ :: *;
	private import SI :: *;
	public import 'Vehicle Usages' :: *;
	public import 'Vehicle Requirements' :: *;
	package 'Vehicle Definitions'{
		part def Vehicle{
			attribute mass : MassValue;
			attribute fuelLevel : Real;
			attribute fuelTankCapacity : Real;
		}
		part def Engine{
			port drivePwrPort : DrivePwrPort;
			perform action 'generate torque' : 'Generate Torque';
		}
		part def Transmission{
			port clutchPort : ClutchPort;
		}
		port def DrivePwrPort;
		port def ClutchPort;
		interface def EngineToTransmissionInterface{
			end drivePwrPort : DrivePwrPort;
			end clutchPort : ClutchPort;
		}
		action def 'Generate Torque';
	}
	package 'Vehicle Usages'{
		public import 'Vehicle Definitions' :: *;
		action 'provide power'{
			action 'generate torque'{
				/* ... */
			}
			//...
		}
		part vehicle1_c1 : Vehicle{
			attribute :>> mass = 2000 [kg];
			perform 'provide power';
			part engine_v1 : Engine{
				port :>> drivePwrPort;
				perform 'provide power'.'generate torque' :>> 'generate torque';
			}
			part transmission : Transmission{
				port :>> clutchPort;
			}
			interface engineToTransmission : EngineToTransmissionInterface connect engine_v1.drivePwrPort to transmission.clutchPort;
		}
		part vehicle1_c2 : Vehicle{
			attribute :>> mass = 2500 [kg];
		}
	}
	package 'Vehicle Requirements'{
		public import 'Vehicle Definitions' :: *;
		requirement def < '1' > MassLimitationRequirement{
			/*
			 * The optional requirement ID  of this requirement ('1') is given after the keyword "id" (using name syntax).
			 * Every requirement is parameterized by a "subject". The "subject" of this requirement is implicitly "Anything".
			 */
			// The requirement text is given by the documentation in the requirement def body.
			doc /* The actual mass shall be less than or equal to the required mass. */
			attribute massActual : MassValue;
			attribute massReqd : MassValue;
			require constraint{
				/*
				 * A constraint can be used to formalize a requirement.
				 */
				massActual <= massReqd
			}
		}
		requirement def < '2' > ReliabilityRequirement;
		requirement < '1.1' > vehicleMass1 : MassLimitationRequirement{
			doc /* The vehicle mass shall be less than or equal to 2000 kg when the fuel tank is full. */
			subject vehicle : Vehicle{
				/*
				 * The subject of this requirement is redefined to be a "Vehicle".
				 */
			}
			attribute : MassValue :>> massActual = vehicle.mass{
				/*
				 * This redefinition binds the vehicle mass to the actual mass.
				 */
			}
			attribute :>> massReqd = 2000 [kg]{
				/*
				 * This redefinition sets the required mass to 2000 kg.
				 */
			}
			assume constraint fuelConstraint{
				/*
				 * A constraint can also be used to specify an assumption.
				 */
				doc /* full fuel tank */
				vehicle.fuelLevel >= vehicle.fuelTankCapacity
			}
		}
		requirement < '2.1' > vehicleMass2 : MassLimitationRequirement{
			doc /* The vehicle mass shall be less than or equal to 2500 kg when the fuel tank is empty. */
			subject vehicle : Vehicle;
			attribute : MassValue :>> massActual = vehicle.mass;
			attribute :>> massReqd = 2500 [kg];
			assume constraint fuelConstraint{
				doc /* empty fuel tank */
				vehicle.fuelLevel == 0.0
			}
		}
		requirement < '2.2' > vehicleReliability2 : ReliabilityRequirement{
			subject vehicle : Vehicle;
		}
		requirement < '3.1' > drivePowerInterface{
			doc /* The engine shall transfer its generated torque to the transmission via the clutch interface. */
			subject drivePwrPort : DrivePwrPort;
		}
		requirement < '3.2' > torqueGeneration{
			doc /* The engine shall generate torque as a function of RPM as shown in Table 1. */
			subject generateTorque : 'Generate Torque';
		}
	}
	part 'vehicle1_c1 Specification Context'{
		private import 'vehicle1-c1 Specification' :: *;
		private import 'engine-v1 Specification' :: *;
		requirement 'vehicle1-c1 Specification'{
			doc /*
		 * This models a "requirement group" as a requirement that references other requirements.
		 */
			subject vehicle : Vehicle;
			requirement ::> vehicleMass1{
				/*
				 * This is a reference to a requirement defined outside the group.
				 * By default, the subject of the requirement is bound to that of the group.
				 */
			}
			// ...
		}
		requirement 'engine-v1 Specification'{
			subject engine : Engine;
			/* 
			 * Here the subjects of the referenced requirements are defined to be specific properties of the
			 * subject of the group.
			 */
			require torqueGeneration{
				in :>> generateTorque = engine.'generate torque';
			}
			require drivePowerInterface{
				in :>> drivePwrPort = engine.drivePwrPort;
			}
		}
		satisfy 'vehicle1-c1 Specification' by vehicle1_c1{
			/*
			 * This asserts that if the assumptions of 'vehicle1-c1 Specification' are true with 'vehicle_c1' as
			 * the subject, then the required constraints are also true.
			 */
		}
		satisfy 'engine-v1 Specification' by vehicle1_c1.engine_v1;
	}
	part 'vehicle1_c2 Specification Context'{
		private import 'vehicle1-c2 Specification' :: *;
		requirement 'vehicle1-c2 Specification'{
			subject vehicle : Vehicle;
			require vehicleMass2;
			require vehicleReliability2;
		}
		satisfy 'vehicle1-c2 Specification' by vehicle1_c2;
	}
}
