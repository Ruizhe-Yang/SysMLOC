package '10b-Trade-off Among Alternative Configurations'{
	private import ScalarValues::Real;
	private import TradeStudies :: *;
	private import Definitions :: *;
	private import Usages :: *;
	package Definitions{
		part def Vehicle;
		part def Engine{
			power : ISQ::PowerValue;
			mass : ISQ::MassValue;
			efficiency : Real;
			reliability : Real;
			cost : Real;
		}
		part def Piston;
		part def Cylinder;
		part def ConnectingRod;
		part def CrankShaft;
		part def '4CylCrankShaft' : CrankShaft;
		part def '6CylCrankShaft' : CrankShaft;
	}
	package Usages{
		part engine : Engine{
			part cyl [ * ] : Cylinder{
				part p [ 1 ] : Piston;
				part rod [ 1 ] : ConnectingRod;
			}
			part cs : CrankShaft;
		}
		variation part engineChoice :> engine{
			variant part '4cylEngine'{
				part [ 4 ] :>> cyl;
				part : '4CylCrankShaft' :>> cs;
			}
			variant part '6cylEngine'{
				part [ 6 ] :>> cyl;
				part : '6CylCrankShaft' :>> cs;
			}
		}
		part vehicle : Vehicle{
			part engine [ 1 ] :> engineChoice = engineChoice::'6cylEngine'{
				assert constraint engineSelectionRational{
					doc /* Selected the best engine based on the 'engineTradeStudy'. */
					engine == Analysis::engineTradeStudy.selectedAlternative
				}
			}
		}
	}
	package Analysis{
		calc def EngineEvaluation{
			doc /* Evaluation function with criteria power, mass, efficency and cost. */
			in power : ISQ::PowerValue;
			in mass : ISQ::MassValue;
			in efficiency : Real;
			in cost : Real;
			return evaluation : Real;
			// Compute evaluation...
		}
		analysis engineTradeStudy : TradeStudy{
			subject [ 1 .. * ] : Engine = all engineChoice;
			objective : MaximizeObjective;
			calc :>> evaluationFunction{
				in part anEngine : Engine :>> alternative;
				calc powerRollup{
					in engine = anEngine;
					return power :> ISQ::power;
				}
				calc massRollup{
					in engine = anEngine;
					return mass :> ISQ::mass;
				}
				calc efficiencyRollup{
					in engine = anEngine;
					return efficiency : Real;
				}
				calc costRollup{
					in engine = anEngine;
					return cost : Real;
				}
				return : Real :>> result = EngineEvaluation( powerRollup.power, massRollup.mass, efficiencyRollup.efficiency, costRollup.cost );
			}
			return part : Engine :>> selectedAlternative;
		}
	}
}
