package '10d-Dynamics Analysis'{
	private import ISQ :: *;
	package VehicleModel{
		part def Vehicle{
			attribute mass :> ISQ::mass;
		}
	}
	package DynamicsModel{
		calc def Acceleration{
			in p : PowerValue;
			in m : MassValue;
			in v : SpeedValue;
			return : AccelerationValue = p / (m * v);
		}
		calc def Velocity{
			in v0 : SpeedValue;
			in a : AccelerationValue;
			in dt : TimeValue;
			return : SpeedValue = v0 + a * dt;
		}
		calc def Position{
			in x0 : LengthValue;
			in v : SpeedValue;
			in dt : TimeValue;
			return : LengthValue = x0 + v * dt;
		}
		action def StraightLineDynamics{
			in power : PowerValue;
			in mass : MassValue;
			in delta_t : TimeValue;
			in x_in : LengthValue;
			in v_in : SpeedValue;
			out x_out : LengthValue = Position(x_in, v_in, delta_t);
			out v_out : SpeedValue = Velocity(v_in, a_out, delta_t);
			out a_out : AccelerationValue = Acceleration(power, mass, v_in);
		}
	}
	package AnalysisModel{
		private import VehicleModel :: *;
		private import DynamicsModel :: *;
		private import SampledFunctions :: *;
		private import ScalarValues::Natural;
		private import SequenceFunctions :: *;
		analysis def DynamicsAnalysis{
			subject vehicle : Vehicle;
			in attribute powerProfile [ * ] :> ISQ::power;
			in attribute initialPosition :> ISQ::length;
			in attribute initialSpeed :> ISQ::speed;
			in attribute deltaT :> ISQ::time;
			return attribute accelerationProfile [ * ] :> ISQ::acceleration := ();
			private attribute position := initialPosition;
			private attribute speed := initialSpeed;
			for i in 1..powerProfile->size()-1{
				perform action dynamics : StraightLineDynamics{
					in power = powerProfile#(i);
					in mass = vehicle.mass;
					in delta_t = deltaT;
					in x_in = position;
					in v_in = speed;
				}
				then assign position := dynamics.x_out;
				then assign speed := dynamics.v_out;
				then assign accelerationProfile := accelerationProfile->including(dynamics.a_out);
			}
		}
	}
}
