private import Views :: *;
// private import library package, not internal Views package!
package '11b-Safety and Security Feaure Views'{
	private import ScalarValues :: *;
	package AnnotationDefinitions{
		metadata def Safety{
			attribute isMandatory : Boolean;
		}
		metadata def Security;
	}
	package PartsTree{
		public import AnnotationDefinitions :: *;
		part vehicle{
			part interior{
				part alarm{
					metadata Security;
				}
				part seatBelt [ 2 ]{
					metadata Safety{
						isMandatory = true;
					}
				}
				part frontSeat [ 2 ];
				part driverAirBag{
					metadata Safety{
						isMandatory = false;
					}
				}
			}
			part bodyAssy{
				part body;
				part bumper{
					metadata Safety{
						isMandatory = true;
					}
				}
				part keylessEntry{
					metadata Security;
				}
			}
			part wheelAssy{
				part wheel [ 2 ];
				part antilockBrakes [ 2 ]{
					metadata Safety{
						isMandatory = false;
					}
				}
			}
		}
	}
	package ViewDefinitions{
		public import AnnotationDefinitions :: *;
		view def SafetyFeatureView{
			/* Parts that contribute to safety. */
			filter @Safety;
			render asTreeDiagram;
		}
		view def SafetyOrSecurityFeatureView{
			/* Parts that contribute to safety OR security. */
			filter @Safety | @Security;
		}
	}
	package Views{
		private import ViewDefinitions :: *;
		private import PartsTree::vehicle;
		view vehicleSafetyFeatureView : SafetyFeatureView{
			expose vehicle;
		}
		view vehicleMandatorySafetyFeatureView :> vehicleSafetyFeatureView{
			expose vehicle :: * :: **;
			filter Safety::isMandatory;
		}
		view vehicleMandatorySafetyFeatureViewStandalone{
			expose vehicle :: ** [ @Safety and Safety::isMandatory ];
			render asElementTable;
		}
	}
}
