package '15_03-Value Expression'{
	private import SI :: *;
	private import USCustomaryUnits :: *;
	part def Vehicle_1{
		attribute mass : MassValue = 1200 [kg];
		attribute length : LengthValue = 4.82 [m];
		part leftFrontWheel : Wheel;
		part rightFrontWheel : Wheel;
	}
	part def Wheel{
		attribute hubDiameter : LengthValue = 18 ['in'];
		attribute width : LengthValue = 245 [mm];
		attribute outerDiameter : LengthValue = (hubDiameter + 2 * tire.height) [mm]{
			doc /*
	         * This binds 'outDiameter' to the result of a computed attribute.
	         * There is no need to mark it as "derived".
	         */
		}
		part tire [ 1 ] : Tire;
	}
	part def Tire{
		attribute profileDepth : LengthValue default 6.0 [mm];
		constraint hasLegalProfileDepth{
			profileDepth >= 3.5 [mm]
		}
		attribute height : LengthValue = 45 [mm];
	}
}
