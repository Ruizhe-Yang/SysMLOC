package '15_04-Logical Expressions'{
	private import ScalarValues :: *;
	part def Engine;
	part def '4CylEngine' : Engine;
	part def '6CylEngine' : Engine;
	part def Transmission;
	part def ManualTransmission : Transmission;
	part def AutomaticTransmission : Transmission;
	part def Vehicle{
		attribute isHighPerformance : Boolean;
		part engine [ 1 ] : Engine;
		part transmission [ 1 ] : Transmission;
		assert constraint{
			if isHighPerformance? engine istype '6CylEngine' else engine istype '4CylEngine'
		}
		assert constraint{
			(engine istype '4CylEngine' and transmission istype ManualTransmission ) xor (engine istype '6CylEngine' and transmission istype AutomaticTransmission )
		}
	}
}
