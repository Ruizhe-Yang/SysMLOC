standard library package AnalysisTooling{
	doc /*
	 * This package contains definitions for metadata annotations related
	 * to analysis tool integration.
	 */
	private import ScalarValues :: *;
	metadata def ToolExecution{
		doc /*
		 * ToolExecution metadata identifies an external analysis tool to be
		 * used to implement the annotated action.
		 */
		attribute toolName : String;
		attribute uri : String;
	}
	metadata def ToolVariable{
		doc /*
		 * ToolVariable metadata is used in the context of an action that has
		 * been annotated with ToolExecution metadata. It is used to annotate
		 * a parameter or other feature of the action with the name of the
		 * variable in the tool that is to correspond to the annotated
		 * feature.
		 */
		attribute name : String;
	}
}
