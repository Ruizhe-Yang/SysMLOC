standard library package TradeStudies{
	doc /*
	 * This package provides a simple framework for defining trade-off study analysis cases.
	 */
	private import Base::Anything;
	private import ScalarValues :: *;
	private import ScalarFunctions :: *;
	private import ControlFunctions :: *;
	abstract calc def EvaluationFunction{
		doc /*
		 * An EvaluationFunction is a calculation that evaluates a TradeStudy alternative,
		 * producing a ScalarValue that can be comparted with the evaluation of other
		 * alternatives.
		 */
		in ref alternative : Anything{
			doc /*
			 * The alternative to be evaluated.
			 */
		}
		return attribute result [ 1 ] : ScalarValue{
			doc /*
			 * A ScalarValue representing the evaluation of the given alternative.
			 */
		}
	}
	abstract requirement def TradeStudyObjective{
		doc /*
		 * A TradeStudyObjective is the base definition for the objective of a TradeStudy.
		 * The requirement is to choose from a given set of alternatives the selectedAlternative
		 * for that has the best evaluation according to a given EvaluationFunction. What
		 * value is considered "best" is not defined in the abstract base definition but must be
		 * computed in any concrete specialization.
		 */
		subject selectedAlternative : Anything{
			doc /*
			 * The alternative that should be selected, as evaluated using the given 
			 * ObjectiveFunction.
			 */
		}
		in ref alternatives [ 1 .. * ] : Anything{
			doc /*
			 * The alternatives being considered in the TradeStudy for which this TradeStudyObjective 
			 * is the objective.
			 */
		}
		in calc eval : EvaluationFunction{
			doc /*
			 * The EvaluationFunction to be used in evaluating the given alternatives.
			 */
		}
		attribute best : ScalarValue{
			doc /*
			 * Out of the evaluation results of all the given alternatives, the one that is considered 
			 * "best", in the sense that it is the value the selectedAlternative should have. This 
			 * value must be computed in any concrete specialization of TradeStudyObjective.
			 */
		}
		require constraint{
			eval(selectedAlternative) == best
		}
	}
	requirement def MinimizeObjective : TradeStudyObjective{
		doc /*
		 * A MinimizeObjective is a TradeStudyObjective that requires that the 
		 * selectedAlternative have the minimum ObjectiveFunction value of all the
		 * given alternatives.
		 */
		doc /*
			 * For a MinimizeObjective, the best value is the minimum one.
			 */
		attribute :>> best = alternatives->minimize{
			in x;
			eval(x)
		}
;
	}
	requirement def MaximizeObjective : TradeStudyObjective{
		doc /*
		 * A MaximizeObjective is a TradeStudyObjective that requires that the 
		 * selectedAlternative have the maximum ObjectiveFunction value of all the
		 * given alternatives.
		 */
		doc /*
			 * For a MinimizeObjective, the best value is the maximum one.
			 */
		attribute :>> best = alternatives->maximize{
			in x;
			eval(x)
		}
;
	}
	abstract analysis def TradeStudy{
		doc /*
		 * A TradeStudy is an analysis case whose subject is a set of alternatives
		 * (at least one) and whose result is a selection of one of those alternatives.
		 * The alternatives are evaluated based on a given ObjectiveFunction and the
		 * selection is made such that it satisfies the objective of the TradeStudy
		 * (which must be a TradeStudyObjective).
		 */
		subject studyAlternatives [ 1 .. * ] : Anything{
			doc /*
			 * The set of alternatives being considered in this TradeStudy. 
			 * 
			 * In a TradeStudy usage, bind this feature to the actual collection of
			 * alternatives to be considered.
			 */
		}
		abstract calc evaluationFunction : EvaluationFunction{
			doc /*
			 * The EvaluationFunction to be used to evaluate the alternatives.
			 * 
			 * In a TradeStudy usage, redefine this feature to provide the desired
			 * calculation (or bind it to a calculation usage that does so).
			 */
		}
		objective tradeStudyObjective : TradeStudyObjective{
			doc /*
			 * The objective of this TradeStudy.
			 * 
			 * Redefine this feature to give it a definition that is a concrete
			 * specialization of TradeStudyObjective. That can either be one of the
			 * specializations provided in this package, or a more specific user-
			 * defined one.
			 */
			subject :>> selectedAlternative;
			in ref :>> alternatives = studyAlternatives;
			in calc :>> eval = evaluationFunction;
		}
		doc /*
			 * The alternative selected by this TradeStudy, which is the one that meets the
			 * requirement of the tradeStudyObjective.
			 */
		return selectedAlternative : Anything = studyAlternatives->selectOne{
			in ref a;
			tradeStudyObjective(selectedAlternative = a)
		}
;
	}
}
