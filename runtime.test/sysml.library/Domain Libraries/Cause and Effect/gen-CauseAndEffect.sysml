standard library package CauseAndEffect{
	doc /* This package provides language-extension metadata for cause-effect modeling. */
	public import CausationConnections :: *;
	private import ScalarValues :: *;
	private import Metaobjects::SemanticMetadata;
	metadata def < cause > CauseMetadata : SemanticMetadata{
		doc /*
		 * CauseMetadata identifies a usage as being a cause occurrence.
		 * It is intended to be used to tag the cause ends of a Multicausation.
		 */
		ref : SysML::Usage :>> annotatedElement;
		ref :>> baseType = causes as SysML::Usage;
	}
	metadata def < effect > EffectMetadata : SemanticMetadata{
		doc /*
		 * EffectMetadata identifies a usage as being an effect occurrence.
		 * It is intended to be used to tag the effect ends of a Multicausation.
		 */
		ref : SysML::Usage :>> annotatedElement;
		ref :>> baseType = effects as SysML::Usage;
	}
	metadata def CausationMetadata{
		doc /*
		 * CausationMetadata allows for the specification of additional metadata about
		 * a cause-effect connection definition or usage.
		 */
		ref : SysML::ConnectionDefinition :> annotatedElement;
		ref : SysML::ConnectionUsage :> annotatedElement;
		attribute isNecessary : Boolean default false{
			doc /* 
			 * Whether all the causes are necessary for all the effects to occur.
			 * If this is false (the default), then some or all of the effects may 
			 * still have occurred even if some of the causes did not.
			 */
		}
		attribute isSufficient : Boolean default false{
			doc /*
			 * Whether the causes were sufficient for all the effects to occur.
			 * If this is false (the default), then it may be the case that some
			 * other occurrences were also necessary for some or all of the effects
			 * to have occurred.
			 */
		}
		attribute probability [ 0 .. 1 ] : Real{
			doc /* The probability that the causes will actually result in effects occurring. */
		}
	}
	metadata def < multicausation > MulticausationSemanticMetadata : CausationMetadata , SemanticMetadata{
		doc /*
		 * MulticausationMetadata is SemanticMetadata for a Multicausation connection.
		 */
		ref :>> baseType = multicausations meta SysML::Usage;
	}
	metadata def < causation > CausationSemanticMetadadata : CausationMetadata , SemanticMetadata{
		doc /*
		 * CausationMetadata is SemanticMetadata for a Causation connection.
		 */
		ref :>> baseType = causations meta SysML::Usage;
	}
}
