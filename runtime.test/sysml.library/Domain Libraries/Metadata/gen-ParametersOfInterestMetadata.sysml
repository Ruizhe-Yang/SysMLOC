standard library package ParametersOfInterestMetadata{
	doc /*
	 * This package contains definitions of metadata to identify key parameters of interest,
	 * including measures of effectiveness (MOE) and other key measures of performance (MOP).
	 */
	private import Metaobjects::SemanticMetadata;
	attribute measuresOfEffectiveness [ * ] nonunique{
		doc /* Base feature for attributes that are measures of effectiveness. */
	}
	attribute measuresOfPerformance [ * ] nonunique{
		doc /* Base feature for attributes that are measures of performance. */
	}
	metadata def < moe > MeasureOfEffectiveness : SemanticMetadata{
		doc /*
	 	 * MeasureOfEffectiveness is semantic metadata for identifying an attribute as a
	 	 * measure of effectiveness.
	 	 */
		: SysML::Usage :>> annotatedElement;
		:>> baseType = measuresOfEffectiveness meta SysML::Usage;
	}
	metadata def < mop > MeasureOfPerformance : SemanticMetadata{
		doc /*
	 	 * MeasureOfPerformance is semantic metadata for identifying an attribute as a
	 	 * measure of performance.
	 	 */
		: SysML::Usage :>> annotatedElement;
		:>> baseType = measuresOfPerformance meta SysML::Usage;
	}
}
