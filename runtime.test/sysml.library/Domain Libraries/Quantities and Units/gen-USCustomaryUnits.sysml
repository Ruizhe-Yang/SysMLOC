standard library package < USCU > USCustomaryUnits{
	doc /*
	 * Measurement unit declarations generated from NIST SP811 Appendix B
	 *
	 * See https://www.nist.gov/pml/special-publication-811/nist-guide-si-appendix-b-conversion-factors/nist-guide-si-appendix-b8
	 */
	private import MeasurementReferences :: *;
	public import ISQ :: *;
	private import SI :: *;
	attribute 'acre (based on US survey foot)' : AreaUnit{
		: ConversionByConvention :>> unitConversion{
			:>> referenceUnit = m^2;
			:>> conversionFactor = 4.046873E+03;
			:>> isExact = false;
		}
	}
	attribute 'acre foot (based on US survey foot)' : VolumeUnit{
		: ConversionByConvention :>> unitConversion{
			:>> referenceUnit = m^3;
			:>> conversionFactor = 1.233489E+03;
			:>> isExact = false;
		}
	}
	attribute < bbl > 'barrel (for petroleum, 42 gallons (US))' : VolumeUnit{
		: ConversionByConvention :>> unitConversion{
			:>> referenceUnit = m^3;
			:>> conversionFactor = 1.589873E-01;
			:>> isExact = false;
		}
	}
	attribute < Btu_IT > 'British thermal unit (IT)' : EnergyUnit{
		: ConversionByConvention :>> unitConversion{
			:>> referenceUnit = J;
			:>> conversionFactor = 1.055056E+03;
			:>> isExact = false;
		}
	}
	alias Btu for Btu_IT;
	attribute < Btu_th > 'British thermal unit (th)' : EnergyUnit{
		: ConversionByConvention :>> unitConversion{
			:>> referenceUnit = J;
			:>> conversionFactor = 1.054350E+03;
			:>> isExact = false;
		}
	}
	attribute < Btu_mean > 'British thermal unit (mean)' : EnergyUnit{
		: ConversionByConvention :>> unitConversion{
			:>> referenceUnit = J;
			:>> conversionFactor = 1.05587E+03;
			:>> isExact = false;
		}
	}
	attribute < 'Btu_39°F' > 'British thermal unit (39 °F)' : EnergyUnit{
		: ConversionByConvention :>> unitConversion{
			:>> referenceUnit = J;
			:>> conversionFactor = 1.05967E+03;
			:>> isExact = false;
		}
	}
	attribute < 'Btu_59°F' > 'British thermal unit (59 °F)' : EnergyUnit{
		: ConversionByConvention :>> unitConversion{
			:>> referenceUnit = J;
			:>> conversionFactor = 1.05480E+03;
			:>> isExact = false;
		}
	}
	attribute < 'Btu_60°F' > 'British thermal unit (60 °F)' : EnergyUnit{
		: ConversionByConvention :>> unitConversion{
			:>> referenceUnit = J;
			:>> conversionFactor = 1.05468E+03;
			:>> isExact = false;
		}
	}
	attribute < 'Btu_IT⋅ft/(h⋅ft²⋅°F)' > 'British thermal unit (IT) foot per hour square foot degree Fahrenheit' : ThermalConductivityUnit = Btu_IT*ft/(h*ft^2*'°F');
	attribute < 'Btu_th⋅ft/(h⋅ft²⋅°F)' > 'British thermal unit (th) foot per hour square foot degree Fahrenheit' : ThermalConductivityUnit = Btu_th*ft/(h*ft^2*'°F');
	attribute < 'Btu_IT⋅in/(h⋅ft²⋅°F)' > 'British thermal unit (IT) inch per hour square foot degree Fahrenheit' : ThermalConductivityUnit = Btu_IT*'in'/(h*ft^2*'°F');
	attribute < 'Btu_th⋅in/(h⋅ft²⋅°F)' > 'British thermal unit (th) inch per hour square foot degree Fahrenheit' : ThermalConductivityUnit = Btu_th*'in'/(h*ft^2*'°F');
	attribute < 'Btu_IT⋅in/(s⋅ft²⋅°F)' > 'British thermal unit (IT) inch per second square foot degree Fahrenheit' : ThermalConductivityUnit = Btu_IT*'in'/(s*ft^2*'°F');
	attribute < 'Btu_th⋅in/(s⋅ft²⋅°F)' > 'British thermal unit (th) inch per second square foot degree Fahrenheit' : ThermalConductivityUnit = Btu_th*'in'/(s*ft^2*'°F');
	//attribute <'Btu_IT/ft³'> 'British thermal unit (IT) per cubic foot' : EnergyDensityUnit = Btu_IT/ft^3;
	//attribute <'Btu_th/ft³'> 'British thermal unit (th) per cubic foot' : EnergyDensityUnit = Btu_th/ft^3;
	attribute < 'Btu_IT/°F' > 'British thermal unit (IT) per degree Fahrenheit' : HeatCapacityUnit = Btu_IT/'°F';
	attribute < 'Btu_th/°F' > 'British thermal unit (th) per degree Fahrenheit' : HeatCapacityUnit = Btu_th/'°F';
	attribute < 'Btu_IT/°R' > 'British thermal unit (IT) per degree Rankine' : HeatCapacityUnit = Btu_IT/'°R';
	attribute < 'Btu_th/°R' > 'British thermal unit (th) per degree Rankine' : HeatCapacityUnit = Btu_th/'°R';
	attribute < 'Btu_IT/h' > 'British thermal unit (IT) per hour' : PowerUnit = Btu_IT/h;
	attribute < 'Btu_th/h' > 'British thermal unit (th) per hour' : PowerUnit = Btu_th/h;
	attribute < 'Btu_IT/(h⋅ft²⋅°F)' > 'British thermal unit (IT) per hour square foot degree Fahrenheit' : CoefficientOfHeatTransferUnit = Btu_IT/(h*ft^2*'°F');
	attribute < 'Btu_th/(h⋅ft²⋅°F)' > 'British thermal unit (th) per hour square foot degree Fahrenheit' : CoefficientOfHeatTransferUnit = Btu_th/(h*ft^2*'°F');
	attribute < 'Btu_th/min' > 'British thermal unit (th) per minute' : PowerUnit = Btu_th/min;
	attribute < 'Btu_IT/lb' > 'British thermal unit (IT) per pound' : SpecificEnergyUnit = Btu_IT/lb;
	attribute < 'Btu_th/lb' > 'British thermal unit (th) per pound' : SpecificEnergyUnit = Btu_th/lb;
	attribute < 'Btu_IT/(lb⋅°F)' > 'British thermal unit (IT) per pound degree Fahrenheit' : SpecificHeatCapacityUnit = Btu_IT/(lb*'°F');
	attribute < 'Btu_th/(lb⋅°F)' > 'British thermal unit (th) per pound degree Fahrenheit' : SpecificHeatCapacityUnit = Btu_th/(lb*'°F');
	attribute < 'Btu_IT/(lb⋅°R)' > 'British thermal unit (IT) per pound degree Rankine' : SpecificHeatCapacityUnit = Btu_IT/(lb*'°R');
	attribute < 'Btu_th/(lb⋅°R)' > 'British thermal unit (th) per pound degree Rankine' : SpecificHeatCapacityUnit = Btu_th/(lb*'°R');
	attribute < 'Btu_IT/s' > 'British thermal unit (IT) per second' : PowerUnit = Btu_IT/s;
	attribute < 'Btu_th/s' > 'British thermal unit (th) per second' : PowerUnit = Btu_th/s;
	attribute < 'Btu_IT/(s⋅ft²⋅°F)' > 'British thermal unit (IT) per second square foot degree Fahrenheit' : CoefficientOfHeatTransferUnit = Btu_IT/(s*ft^2*'°F');
	attribute < 'Btu_th/(s⋅ft²⋅°F)' > 'British thermal unit (th) per second square foot degree Fahrenheit' : CoefficientOfHeatTransferUnit = Btu_th/(s*ft^2*'°F');
	//attribute <'Btu_IT/ft²'> 'British thermal unit (IT) per square foot' : SurfaceHeatDensityUnit = Btu_IT/ft^2;
	//attribute <'Btu_th/ft²'> 'British thermal unit (th) per square foot' : SurfaceHeatDensityUnit = Btu_th/ft^2;
	attribute < 'Btu_IT/(ft²⋅h)' > 'British thermal unit (IT) per square foot hour' : DensityOfHeatFlowRateUnit = Btu_IT/(ft^2*h);
	attribute < 'Btu_th/(ft²⋅h)' > 'British thermal unit (th) per square foot hour' : DensityOfHeatFlowRateUnit = Btu_th/(ft^2*h);
	attribute < 'Btu_th/(ft²⋅min)' > 'British thermal unit (th) per square foot minute' : DensityOfHeatFlowRateUnit = Btu_th/(ft^2*min);
	attribute < 'Btu_IT/(ft²⋅s)' > 'British thermal unit (IT) per square foot second' : DensityOfHeatFlowRateUnit = Btu_IT/(ft^2*s);
	attribute < 'Btu_th/(ft²⋅s)' > 'British thermal unit (th) per square foot second' : DensityOfHeatFlowRateUnit = Btu_th/(ft^2*s);
	attribute < 'Btu_th/(in²⋅s)' > 'British thermal unit (th) per square inch second' : DensityOfHeatFlowRateUnit = Btu_th/('in'^2*s);
	attribute < bu > 'bushel (US)' : VolumeUnit{
		: ConversionByConvention :>> unitConversion{
			:>> referenceUnit = m^3;
			:>> conversionFactor = 3.523907E-02;
			:>> isExact = false;
		}
	}
	attribute < 'cd/in²' > 'candela per square inch' : LuminanceUnit = cd/'in'^2;
	attribute < ch > 'chain (based on US survey foot)' : LengthUnit{
		: ConversionByConvention :>> unitConversion{
			:>> referenceUnit = m;
			:>> conversionFactor = 2.011684E+01;
			:>> isExact = false;
		}
	}
	attribute 'circular mil' : AreaUnit{
		: ConversionByConvention :>> unitConversion{
			:>> referenceUnit = m^2;
			:>> conversionFactor = 5.067075E-10;
			:>> isExact = false;
		}
	}
	attribute 'clo' : ThermalInsulanceUnit{
		: ConversionByConvention :>> unitConversion{
			:>> referenceUnit = m^2*K/W;
			:>> conversionFactor = 1.55E-01;
			:>> isExact = false;
		}
	}
	attribute 'cord (128 ft^3)' : VolumeUnit{
		: ConversionByConvention :>> unitConversion{
			:>> referenceUnit = m^3;
			:>> conversionFactor = 3.624556E+00;
			:>> isExact = false;
		}
	}
	attribute < 'ft³' > 'cubic foot' : VolumeUnit = ft^3;
	attribute < 'ft³/min' > 'cubic foot per minute' : VolumeFlowRateUnit = ft^3/min;
	attribute < 'ft³/s' > 'cubic foot per second' : VolumeFlowRateUnit = ft^3/s;
	attribute < 'in³' > 'cubic inch' : VolumeUnit = 'in'^3;
	attribute < 'in³/min' > 'cubic inch per minute' : VolumeFlowRateUnit = 'in'^3/min;
	attribute < 'mi³' > 'cubic mile' : VolumeUnit = mi^3;
	attribute < 'yd³' > 'cubic yard' : VolumeUnit = yd^3;
	attribute < 'yd³/min' > 'cubic yard per minute' : VolumeFlowRateUnit = yd^3/min;
	attribute 'cup (US)' : VolumeUnit{
		: ConversionByConvention :>> unitConversion{
			:>> referenceUnit = m^3;
			:>> conversionFactor = 2.365882E-04;
			:>> isExact = false;
		}
	}
	attribute < '°F' > 'degree Fahrenheit (temperature difference)' : TemperatureDifferenceUnit{
		: ConversionByConvention :>> unitConversion{
			:>> referenceUnit = K;
			:>> conversionFactor = 5/9;
			:>> isExact = true;
		}
	}
	attribute < '°F⋅h/Btu_IT' > 'degree Fahrenheit hour per British thermal unit (IT)' : ThermalResistanceUnit = '°F'*h/Btu_IT;
	attribute < '°F⋅h/Btu_th' > 'degree Fahrenheit hour per British thermal unit (th)' : ThermalResistanceUnit = '°F'*h/Btu_th;
	attribute < '°F⋅h⋅ft²/Btu_IT' > 'degree Fahrenheit hour square foot per British thermal unit (IT)' : ThermalInsulanceUnit = '°F'*h*ft^2/Btu_IT;
	attribute < '°F⋅h⋅ft²/Btu_th' > 'degree Fahrenheit hour square foot per British thermal unit (th)' : ThermalInsulanceUnit = '°F'*h*ft^2/Btu_th;
	//attribute <'°F⋅h⋅ft²/(Btu_IT⋅in)'> 'degree Fahrenheit hour square foot per British thermal unit (IT) inch' : ThermalResistivityUnit = '°F'*h*ft^2/(Btu_IT*'in');
	//attribute <'°F⋅h⋅ft²/(Btu_th⋅in)'> 'degree Fahrenheit hour square foot per British thermal unit (th) inch' : ThermalResistivityUnit = '°F'*h*ft^2/(Btu_th*'in');
	attribute < '°F⋅s/Btu_IT' > 'degree Fahrenheit second per British thermal unit (IT)' : ThermalResistanceUnit = '°F'*s/Btu_IT;
	attribute < '°F⋅s/Btu_th' > 'degree Fahrenheit second per British thermal unit (th)' : ThermalResistanceUnit = '°F'*s/Btu_th;
	attribute < '°R' > 'degree Rankine' : ThermodynamicTemperatureUnit : TemperatureDifferenceUnit{
		: ConversionByConvention :>> unitConversion{
			:>> referenceUnit = K;
			:>> conversionFactor = 5/9;
			:>> isExact = true;
		}
		:>> ThermodynamicTemperatureUnit::quantityDimension :>> TemperatureDifferenceUnit::quantityDimension{
			:>> ThermodynamicTemperatureUnit::quantityDimension::quantityPowerFactors :>> TemperatureDifferenceUnit::quantityDimension::quantityPowerFactors;
		}
	}
	attribute 'fathom (based on US survey foot)' : LengthUnit{
		: ConversionByConvention :>> unitConversion{
			:>> referenceUnit = m;
			:>> conversionFactor = 1.828804E+00;
			:>> isExact = false;
		}
	}
	attribute < floz > 'fluid ounce (US)' : VolumeUnit{
		: ConversionByConvention :>> unitConversion{
			:>> referenceUnit = m^3;
			:>> conversionFactor = 2.957353E-05;
			:>> isExact = false;
		}
	}
	attribute < ft > 'foot' : LengthUnit{
		: ConversionByConvention :>> unitConversion{
			:>> referenceUnit = m;
			:>> conversionFactor = 3.048E-01;
		}
	}
	attribute 'foot (US survey)' : LengthUnit{
		: ConversionByConvention :>> unitConversion{
			:>> referenceUnit = m;
			:>> conversionFactor = 3.048006E-01;
			:>> isExact = false;
		}
	}
	attribute 'footcandle' : IlluminanceUnit{
		: ConversionByConvention :>> unitConversion{
			:>> referenceUnit = lx;
			:>> conversionFactor = 1.076391E+01;
			:>> isExact = false;
		}
	}
	attribute 'footlambert' : LuminanceUnit{
		: ConversionByConvention :>> unitConversion{
			:>> referenceUnit = cd/m^2;
			:>> conversionFactor = 3.426259E+00;
			:>> isExact = false;
		}
	}
	attribute < ftHg > 'foot of mercury, conventional' : PressureUnit{
		: ConversionByConvention :>> unitConversion{
			:>> referenceUnit = Pa;
			:>> conversionFactor = 4.063666E+04;
			:>> isExact = false;
		}
	}
	attribute 'foot of water (39.2 °F)' : PressureUnit{
		: ConversionByConvention :>> unitConversion{
			:>> referenceUnit = Pa;
			:>> conversionFactor = 2.98898E+03;
			:>> isExact = false;
		}
	}
	attribute < ftH2O > 'foot of water, conventional' : PressureUnit{
		: ConversionByConvention :>> unitConversion{
			:>> referenceUnit = Pa;
			:>> conversionFactor = 2.989067E+03;
			:>> isExact = false;
		}
	}
	attribute < 'ft/h' > 'foot per hour' : SpeedUnit = ft/h;
	attribute < 'ft/min' > 'foot per minute' : SpeedUnit = ft/min;
	attribute < 'ft/s' > 'foot per second' : SpeedUnit = ft/s;
	attribute < 'ft/s²' > 'foot per second squared' : AccelerationUnit = ft/s^2;
	attribute 'foot poundal' : EnergyUnit{
		: ConversionByConvention :>> unitConversion{
			:>> referenceUnit = J;
			:>> conversionFactor = 4.214011E-02;
			:>> isExact = false;
		}
	}
	attribute < 'ft⋅lbf' > 'foot pound-force' : EnergyUnit = ft*lbf;
	attribute < 'ft⋅lbf/h' > 'foot pound-force per hour' : PowerUnit = ft*lbf/h;
	attribute < 'ft⋅lbf/min' > 'foot pound-force per minute' : PowerUnit = ft*lbf/min;
	attribute < 'ft⋅lbf/s' > 'foot pound-force per second' : PowerUnit = ft*lbf/s;
	attribute < 'ft⁴' > 'foot to the fourth power' : SecondAxialMomentOfAreaUnit = ft^4;
	attribute < gal > 'gallon (US)' : VolumeUnit{
		: ConversionByConvention :>> unitConversion{
			:>> referenceUnit = m^3;
			:>> conversionFactor = 3.785412E-03;
			:>> isExact = false;
		}
	}
	attribute < 'gal/d' > 'gallon (US) per day' : VolumeFlowRateUnit = gal/d;
	//attribute <'gal/(hp⋅h)'> 'gallon (US) per horsepower hour' : EnergySpecificVolumeUnit = gal/(hp*h);
	attribute < 'gal/min' > 'gallon (US) per minute (gpm)' : VolumeFlowRateUnit = gal/min;
	attribute < gi > 'gill (US)' : VolumeUnit{
		: ConversionByConvention :>> unitConversion{
			:>> referenceUnit = m^3;
			:>> conversionFactor = 1.182941E-04;
			:>> isExact = false;
		}
	}
	attribute < gr > 'grain' : MassUnit{
		: ConversionByConvention :>> unitConversion{
			:>> referenceUnit = kg;
			:>> conversionFactor = 6.479891E-05;
		}
	}
	attribute < 'gr/gal' > 'grain per gallon (US)' : MassDensityUnit = gr/gal;
	attribute < hp > 'horsepower (550 ft*lbf/s)' : PowerUnit{
		: ConversionByConvention :>> unitConversion{
			:>> referenceUnit = W;
			:>> conversionFactor = 7.456999E+02;
			:>> isExact = false;
		}
	}
	attribute 'horsepower (boiler)' : PowerUnit{
		: ConversionByConvention :>> unitConversion{
			:>> referenceUnit = W;
			:>> conversionFactor = 9.80950E+03;
			:>> isExact = false;
		}
	}
	attribute 'horsepower (electric)' : PowerUnit{
		: ConversionByConvention :>> unitConversion{
			:>> referenceUnit = W;
			:>> conversionFactor = 7.46E+02;
		}
	}
	attribute 'horsepower (water)' : PowerUnit{
		: ConversionByConvention :>> unitConversion{
			:>> referenceUnit = W;
			:>> conversionFactor = 7.46043E+02;
			:>> isExact = false;
		}
	}
	attribute 'hundredweight (long, 112 lb)' : MassUnit{
		: ConversionByConvention :>> unitConversion{
			:>> referenceUnit = kg;
			:>> conversionFactor = 5.080235E+01;
			:>> isExact = false;
		}
	}
	attribute 'hundredweight (short, 100 lb)' : MassUnit{
		: ConversionByConvention :>> unitConversion{
			:>> referenceUnit = kg;
			:>> conversionFactor = 4.535924E+01;
			:>> isExact = false;
		}
	}
	attribute < 'in' > 'inch' : LengthUnit{
		: ConversionByConvention :>> unitConversion{
			:>> referenceUnit = m;
			:>> conversionFactor = 2.54E-02;
		}
	}
	attribute 'inch of mercury (32 °F)' : PressureUnit{
		: ConversionByConvention :>> unitConversion{
			:>> referenceUnit = Pa;
			:>> conversionFactor = 3.38638E+03;
			:>> isExact = false;
		}
	}
	attribute 'inch of mercury (60 °F)' : PressureUnit{
		: ConversionByConvention :>> unitConversion{
			:>> referenceUnit = Pa;
			:>> conversionFactor = 3.37685E+03;
			:>> isExact = false;
		}
	}
	attribute < inHg > 'inch of mercury, conventional' : PressureUnit{
		: ConversionByConvention :>> unitConversion{
			:>> referenceUnit = Pa;
			:>> conversionFactor = 3.386389E+03;
			:>> isExact = false;
		}
	}
	attribute 'inch of water (39.2 °F)' : PressureUnit{
		: ConversionByConvention :>> unitConversion{
			:>> referenceUnit = Pa;
			:>> conversionFactor = 2.49082E+02;
			:>> isExact = false;
		}
	}
	attribute 'inch of water (60 °F)' : PressureUnit{
		: ConversionByConvention :>> unitConversion{
			:>> referenceUnit = Pa;
			:>> conversionFactor = 2.4884E+02;
			:>> isExact = false;
		}
	}
	attribute < inH2O > 'inch of water, conventional' : PressureUnit{
		: ConversionByConvention :>> unitConversion{
			:>> referenceUnit = Pa;
			:>> conversionFactor = 2.490889E+02;
			:>> isExact = false;
		}
	}
	attribute < 'in/s' > 'inch per second' : SpeedUnit = 'in'/s;
	attribute < 'in/s²' > 'inch per second squared' : AccelerationUnit = 'in'/s^2;
	attribute < 'in⁴' > 'inch to the fourth power' : SecondAxialMomentOfAreaUnit = 'in'^4;
	attribute < kip > 'kip (1 kip = 1000 lbf)' : ForceUnit{
		: ConversionByConvention :>> unitConversion{
			:>> referenceUnit = N;
			:>> conversionFactor = 4.448222E+03;
			:>> isExact = false;
		}
	}
	attribute < 'kip/in²' > 'kip per square inch (ksi)' : PressureUnit = kip/'in'^2;
	attribute < knot > 'knot (nautical mile per hour)' : SpeedUnit{
		: ConversionByConvention :>> unitConversion{
			:>> referenceUnit = m/s;
			:>> conversionFactor = 5.144444E-01;
			:>> isExact = false;
		}
	}
	//attribute <'cal_th/cm²'> 'langley' : SurfaceHeatDensityUnit = cal_th/cm^2;
	attribute < 'lm/ft²' > 'lumen per square foot' : IlluminanceUnit = lm/ft^2;
	attribute 'microinch' : LengthUnit{
		: ConversionByConvention :>> unitConversion{
			:>> referenceUnit = m;
			:>> conversionFactor = 2.54E-08;
		}
	}
	attribute < mil > 'mil (0.001 in)' : LengthUnit{
		: ConversionByConvention :>> unitConversion{
			:>> referenceUnit = m;
			:>> conversionFactor = 2.54E-05;
		}
	}
	attribute < mi > 'mile' : LengthUnit{
		: ConversionByConvention :>> unitConversion{
			:>> referenceUnit = m;
			:>> conversionFactor = 1.609344E+03;
		}
	}
	attribute 'mile (based on US survey foot)' : LengthUnit{
		: ConversionByConvention :>> unitConversion{
			:>> referenceUnit = m;
			:>> conversionFactor = 1.609347E+03;
			:>> isExact = false;
		}
	}
	attribute < nmi > 'mile, nautical' : LengthUnit{
		: ConversionByConvention :>> unitConversion{
			:>> referenceUnit = m;
			:>> conversionFactor = 1.852E+03;
		}
	}
	alias NM for nmi;
	//attribute <'mi/gal'> 'mile per gallon (US)' : FuelEconomyUnit = mi/gal;
	//alias mpg for 'mi/gal';
	attribute < 'mi/h' > 'mile per hour' : SpeedUnit = mi/h;
	alias mph for 'mi/h';
	attribute < 'mi/min' > 'mile per minute' : SpeedUnit = mi/min;
	attribute < 'mi/s' > 'mile per second' : SpeedUnit = mi/s;
	attribute 'ohm circular-mil per foot' : ResistivityUnit{
		: ConversionByConvention :>> unitConversion{
			:>> referenceUnit = 'Ω'*m;
			:>> conversionFactor = 1.662426E-09;
			:>> isExact = false;
		}
	}
	attribute < oz > 'ounce (avoirdupois)' : MassUnit{
		: ConversionByConvention :>> unitConversion{
			:>> referenceUnit = kg;
			:>> conversionFactor = 2.834952E-02;
			:>> isExact = false;
		}
	}
	attribute 'ounce (US fluid)' : VolumeUnit{
		: ConversionByConvention :>> unitConversion{
			:>> referenceUnit = m^3;
			:>> conversionFactor = 2.957353E-05;
			:>> isExact = false;
		}
	}
	attribute < ozf > 'ounce (avoirdupois)-force' : ForceUnit{
		: ConversionByConvention :>> unitConversion{
			:>> referenceUnit = N;
			:>> conversionFactor = 2.780139E-01;
			:>> isExact = false;
		}
	}
	attribute < 'ozf⋅in' > 'ounce (avoirdupois)-force inch' : MomentOfForceUnit = ozf*'in';
	attribute < 'oz/in³' > 'ounce (avoirdupois) per cubic inch' : MassDensityUnit = oz/'in'^3;
	attribute < 'oz/gal' > 'ounce (avoirdupois) per gallon (US)' : MassDensityUnit = oz/gal;
	attribute < 'oz/ft²' > 'ounce (avoirdupois) per square foot' : SurfaceMassDensityUnit = oz/ft^2;
	attribute < 'oz/in²' > 'ounce (avoirdupois) per square inch' : SurfaceMassDensityUnit = oz/'in'^2;
	attribute < 'oz/yd²' > 'ounce (avoirdupois) per square yard' : SurfaceMassDensityUnit = oz/yd^2;
	attribute < pk > 'peck (US)' : VolumeUnit{
		: ConversionByConvention :>> unitConversion{
			:>> referenceUnit = m^3;
			:>> conversionFactor = 8.809768E-03;
			:>> isExact = false;
		}
	}
	//attribute 'perm (0 °C)' : VapourTransmissionUnit { :>> unitConversion: ConversionByConvention { :>> referenceUnit = kg/(Pa*s*m^2); :>> conversionFactor = 5.72135E-11; :>> isExact = false; } }
	//attribute 'perm (23 °C)' : VapourTransmissionUnit { :>> unitConversion: ConversionByConvention { :>> referenceUnit = kg/(Pa*s*m^2); :>> conversionFactor = 5.74525E-11; :>> isExact = false; } }
	//attribute 'perm inch (0 °C)' : VapourTransmissionUnit { :>> unitConversion: ConversionByConvention { :>> referenceUnit = kg/('Pa·s·m'); :>> conversionFactor = 1.45322E-12; :>> isExact = false; } }
	//attribute 'perm inch (23 °C)' : VapourTransmissionUnit { :>> unitConversion: ConversionByConvention { :>> referenceUnit = kg/('Pa·s·m'); :>> conversionFactor = 1.45929E-12; :>> isExact = false; } }
	attribute < pica > 'pica (computer) (1/6 in)' : LengthUnit{
		: ConversionByConvention :>> unitConversion{
			:>> referenceUnit = m;
			:>> conversionFactor = 4.233333E-03;
			:>> isExact = false;
		}
	}
	attribute 'pica (printer′s)' : LengthUnit{
		: ConversionByConvention :>> unitConversion{
			:>> referenceUnit = m;
			:>> conversionFactor = 4.217518E-03;
			:>> isExact = false;
		}
	}
	attribute < drypt > 'pint (US dry)' : VolumeUnit{
		: ConversionByConvention :>> unitConversion{
			:>> referenceUnit = m^3;
			:>> conversionFactor = 5.506105E-04;
			:>> isExact = false;
		}
	}
	attribute < liqpt > 'pint (US liquid)' : VolumeUnit{
		: ConversionByConvention :>> unitConversion{
			:>> referenceUnit = m^3;
			:>> conversionFactor = 4.731765E-04;
			:>> isExact = false;
		}
	}
	attribute < pt > 'point (computer) (1/72 in)' : LengthUnit{
		: ConversionByConvention :>> unitConversion{
			:>> referenceUnit = m;
			:>> conversionFactor = 3.527778E-04;
			:>> isExact = false;
		}
	}
	attribute 'point (printer′s)' : LengthUnit{
		: ConversionByConvention :>> unitConversion{
			:>> referenceUnit = m;
			:>> conversionFactor = 3.514598E-04;
			:>> isExact = false;
		}
	}
	attribute < lb > 'pound (avoirdupois)' : MassUnit{
		: ConversionByConvention :>> unitConversion{
			:>> referenceUnit = kg;
			:>> conversionFactor = 4.535924E-01;
			:>> isExact = false;
		}
	}
	attribute < 'lb⋅ft²' > 'pound foot squared' : MomentOfInertiaUnit = lb*ft^2;
	attribute < lbf > 'pound-force' : ForceUnit{
		: ConversionByConvention :>> unitConversion{
			:>> referenceUnit = N;
			:>> conversionFactor = 4.448222E+00;
			:>> isExact = false;
		}
	}
	attribute < 'lbf⋅ft' > 'pound-force foot' : MomentOfForceUnit = lbf*ft;
	attribute < 'lbf⋅ft/in' > 'pound-force foot per inch' : ForceUnit = lbf*ft/'in';
	attribute < 'lbf⋅in' > 'pound-force inch' : MomentOfForceUnit = lbf*'in';
	attribute < 'lbf⋅in/in' > 'pound-force inch per inch' : ForceUnit = lbf*'in'/'in';
	attribute < 'lbf/ft' > 'pound-force per foot' : SurfaceTensionUnit = lbf/ft;
	attribute < 'lbf/in' > 'pound-force per inch' : SurfaceTensionUnit = lbf/'in';
	//attribute 'pound-force per pound (lbf/lb) (thrust to mass ratio)' : ThrustToMassRatioUnit { :>> unitConversion: ConversionByConvention { :>> referenceUnit = N/kg; :>> conversionFactor = 9.80665E+00; } }
	attribute < 'lbf/ft²' > 'pound-force per square foot' : PressureUnit = lbf/ft^2;
	attribute < 'lbf/in²' > 'pound-force per square inch' : PressureUnit = lbf/'in'^2;
	alias psi for 'lbf/in²';
	attribute < 'lbf⋅s/ft²' > 'pound-force second per square foot' : DynamicViscosityUnit = lbf*s/ft^2;
	attribute < 'lbf⋅s/in²' > 'pound-force second per square inch' : DynamicViscosityUnit = lbf*s/'in'^2;
	attribute < 'lb⋅in²' > 'pound inch squared' : MomentOfInertiaUnit = lb*'in'^2;
	attribute < 'lb/ft³' > 'pound per cubic foot' : MassDensityUnit = lb/ft^3;
	attribute < 'lb/in³' > 'pound per cubic inch' : MassDensityUnit = lb/'in'^3;
	attribute < 'lb/yd³' > 'pound per cubic yard' : MassDensityUnit = lb/yd^3;
	attribute < 'lb/ft' > 'pound per foot' : LinearMassDensityUnit = lb/ft;
	attribute < 'lb/(ft⋅h)' > 'pound per foot hour' : DynamicViscosityUnit = lb/(ft*h);
	attribute < 'lb/(ft⋅s)' > 'pound per foot second' : DynamicViscosityUnit = lb/(ft*s);
	attribute < 'lb/gal' > 'pound per gallon (US)' : MassDensityUnit = lb/gal;
	//attribute <'lb/(hp⋅h)'> 'pound per horsepower hour' : FuelConsumptionUnit = lb/(hp*h);
	attribute < 'lb/h' > 'pound per hour' : MassFlowRateUnit = lb/h;
	attribute < 'lb/in' > 'pound per inch' : LinearMassDensityUnit = lb/'in';
	attribute < 'lb/min' > 'pound per minute' : MassFlowRateUnit = lb/min;
	attribute < 'lb/s' > 'pound per second' : MassFlowRateUnit = lb/s;
	attribute < 'lb/ft²' > 'pound per square foot' : SurfaceMassDensityUnit = lb/ft^2;
	attribute < 'lb/in²' > 'pound per square inch (not pound-force)' : SurfaceMassDensityUnit = lb/'in'^2;
	attribute < 'lb/yd' > 'pound per yard' : LinearMassDensityUnit = lb/yd;
	attribute 'pound-force per square inch (psi)' : PressureUnit = lbf/'in'^2;
	attribute 'quad (10^15 Btu_IT)' : EnergyUnit{
		: ConversionByConvention :>> unitConversion{
			:>> referenceUnit = J;
			:>> conversionFactor = 1.055056E+18;
			:>> isExact = false;
		}
	}
	attribute < dryqt > 'quart (US dry)' : VolumeUnit{
		: ConversionByConvention :>> unitConversion{
			:>> referenceUnit = m^3;
			:>> conversionFactor = 1.101221E-03;
			:>> isExact = false;
		}
	}
	attribute < liqqt > 'quart (US liquid)' : VolumeUnit{
		: ConversionByConvention :>> unitConversion{
			:>> referenceUnit = m^3;
			:>> conversionFactor = 9.463529E-04;
			:>> isExact = false;
		}
	}
	attribute < rd > 'rod (based on US survey foot)' : LengthUnit{
		: ConversionByConvention :>> unitConversion{
			:>> referenceUnit = m;
			:>> conversionFactor = 5.029210E+00;
			:>> isExact = false;
		}
	}
	attribute < slug > 'slug' : MassUnit{
		: ConversionByConvention :>> unitConversion{
			:>> referenceUnit = kg;
			:>> conversionFactor = 1.459390E+01;
			:>> isExact = false;
		}
	}
	attribute < 'slug/ft³' > 'slug per cubic foot' : MassDensityUnit = slug/ft^3;
	attribute < 'slug/(ft⋅s)' > 'slug per foot second' : DynamicViscosityUnit = slug/(ft*s);
	attribute < 'ft²' > 'square foot' : AreaUnit = ft^2;
	attribute < 'ft²/h' > 'square foot per hour' : KinematicViscosityUnit = ft^2/h;
	attribute < 'ft²/s' > 'square foot per second' : KinematicViscosityUnit = ft^2/s;
	attribute < 'in²' > 'square inch' : AreaUnit = 'in'^2;
	attribute < 'mi²' > 'square mile' : AreaUnit = mi^2;
	attribute 'square mile (based on US survey foot)' : AreaUnit{
		: ConversionByConvention :>> unitConversion{
			:>> referenceUnit = m^2;
			:>> conversionFactor = 2.589998E+06;
			:>> isExact = false;
		}
	}
	attribute < 'yd²' > 'square yard' : AreaUnit = yd^2;
	attribute 'tablespoon' : VolumeUnit{
		: ConversionByConvention :>> unitConversion{
			:>> referenceUnit = m^3;
			:>> conversionFactor = 1.478676E-05;
			:>> isExact = false;
		}
	}
	attribute 'teaspoon' : VolumeUnit{
		: ConversionByConvention :>> unitConversion{
			:>> referenceUnit = m^3;
			:>> conversionFactor = 4.928922E-06;
			:>> isExact = false;
		}
	}
	attribute 'therm (EC)' : EnergyUnit{
		: ConversionByConvention :>> unitConversion{
			:>> referenceUnit = J;
			:>> conversionFactor = 1.05506E+08;
		}
	}
	attribute 'therm (US)' : EnergyUnit{
		: ConversionByConvention :>> unitConversion{
			:>> referenceUnit = J;
			:>> conversionFactor = 1.054804E+08;
		}
	}
	attribute < AT > 'ton, assay' : MassUnit{
		: ConversionByConvention :>> unitConversion{
			:>> referenceUnit = kg;
			:>> conversionFactor = 2.916667E-02;
			:>> isExact = false;
		}
	}
	attribute 'ton-force (2000 lbf)' : ForceUnit{
		: ConversionByConvention :>> unitConversion{
			:>> referenceUnit = N;
			:>> conversionFactor = 8.896443E+03;
			:>> isExact = false;
		}
	}
	attribute 'ton, long (2240 lb)' : MassUnit{
		: ConversionByConvention :>> unitConversion{
			:>> referenceUnit = kg;
			:>> conversionFactor = 1.016047E+03;
			:>> isExact = false;
		}
	}
	attribute 'ton, long, per cubic yard' : MassDensityUnit{
		: ConversionByConvention :>> unitConversion{
			:>> referenceUnit = kg/m^3;
			:>> conversionFactor = 1.328939E+03;
			:>> isExact = false;
		}
	}
	attribute 'ton of refrigeration (12 000 Btu_IT/h)' : PowerUnit{
		: ConversionByConvention :>> unitConversion{
			:>> referenceUnit = W;
			:>> conversionFactor = 3.516853E+03;
			:>> isExact = false;
		}
	}
	attribute 'ton, register' : VolumeUnit{
		: ConversionByConvention :>> unitConversion{
			:>> referenceUnit = m^3;
			:>> conversionFactor = 2.831685E+00;
			:>> isExact = false;
		}
	}
	attribute 'ton, short (2000 lb)' : MassUnit{
		: ConversionByConvention :>> unitConversion{
			:>> referenceUnit = kg;
			:>> conversionFactor = 9.071847E+02;
			:>> isExact = false;
		}
	}
	attribute 'ton, short, per cubic yard' : MassDensityUnit{
		: ConversionByConvention :>> unitConversion{
			:>> referenceUnit = kg/m^3;
			:>> conversionFactor = 1.186553E+03;
			:>> isExact = false;
		}
	}
	attribute 'ton, short, per hour' : MassFlowRateUnit{
		: ConversionByConvention :>> unitConversion{
			:>> referenceUnit = kg/s;
			:>> conversionFactor = 2.519958E-01;
			:>> isExact = false;
		}
	}
	attribute 'unit pole' : MagneticFluxUnit{
		: ConversionByConvention :>> unitConversion{
			:>> referenceUnit = Wb;
			:>> conversionFactor = 1.256637E-07;
			:>> isExact = false;
		}
	}
	attribute < 'W/in²' > 'watt per square inch' : DensityOfHeatFlowRateUnit = W/'in'^2;
	attribute < yd > 'yard' : LengthUnit{
		: ConversionByConvention :>> unitConversion{
			:>> referenceUnit = m;
			:>> conversionFactor = 9.144E-01;
		}
	}
	attribute < '°F_abs' > 'degree fahrenheit (absolute temperature scale)' : IntervalScale{
		doc /*
		 * degree Fahrenheit interval scale for absolute (thermodynamic) temperature quantities
		 *
	     * The interval scale is defined with an explicit transformation with respect to 
	     * the kelvin thermodynamic temperature scale that specifies the zero shift.
		 */
		:>> unit = '°F';
		private attribute temperatureWaterAtFreezingPointInF : DefinitionalQuantityValue{
			:>> num = 32.0;
			:>> definition = "temperature in degree Fahrenheit of pure water at freezing point";
		}
		private attribute fahrenheitToCelsiusScaleMapping : QuantityValueMapping{
			:>> mappedQuantityValue = temperatureWaterAtFreezingPointInF;
			:>> referenceQuantityValue = '°C_abs'.temperatureWaterAtFreezingPointInC;
		}
		attribute :>> definitionalQuantityValues = temperatureWaterAtFreezingPointInF;
		attribute :>> quantityValueMapping = fahrenheitToCelsiusScaleMapping;
		/* CoordinateFramePlacement (zero shift) w.r.t. the kelvin thermodynamic temperature scale */
		private attribute zeroDegreeFahrenheitInKelvin : ThermodynamicTemperatureValue = 229835/900 [K];
		attribute zeroDegreeFahrenheitToKelvinShift : CoordinateFramePlacement :>> transformation{
			:>> source = K;
			:>> origin = zeroDegreeFahrenheitInKelvin;
		}
	}
}
