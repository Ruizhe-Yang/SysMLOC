standard library package RequirementDerivation{
	doc /* This package provides language-extension metadata for modeling requirement derivation. */
	public import DerivationConnections :: *;
	private import Metaobjects::SemanticMetadata;
	metadata def < original > OriginalRequirementMetadata : SemanticMetadata{
		doc /*
		 * OriginalRequirementMetadata identifies a usage as an original requirement.
		 * It is intended to be used to tag the original requirement end of a Derivation.
		 */
		: SysML::Usage :> annotatedElement;
		:>> baseType = originalRequirements meta SysML::Usage;
	}
	metadata def < derive > DerivedRequirementMetadata : SemanticMetadata{
		doc /*
		 * DerivedRequirementMetadata identifies a usage as a derived requirement.
		 * It is intended to be used to tag the derived requirement ends of a Derivation.
		 */
		: SysML::Usage :> annotatedElement;
		:>> baseType = derivedRequirements meta SysML::Usage;
	}
	metadata def < derivation > DerivationMetadata : SemanticMetadata{
		doc /*
		 * DerivationMetadata is SemanticMetadata for a Derivation connection.
		 */
		: SysML::ConnectionDefinition :> annotatedElement;
		: SysML::ConnectionUsage :> annotatedElement;
		:>> baseType = derivations meta SysML::Usage;
	}
}
