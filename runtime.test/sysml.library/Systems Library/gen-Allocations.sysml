standard library package Allocations{
	doc /*
	 * This package defines the base types for allocations and related structural elements
	 * in the SysML language.
	 */
	private import Base::Anything;
	private import Connections :: *;
	allocation def Allocation : BinaryConnection{
		doc /*
		 * Allocation is the most general class of allocation, represented as a connection 
		 * between the source of the allocation and the target. Allocation is the base type 
		 * of all AllocationDefinitions.
		 */
		end source : Anything :>> BinaryConnection::source;
		end target : Anything :>> BinaryConnection::target;
	}
	abstract allocation allocations [ 0 .. * ] nonunique : Allocation :> binaryConnections{
		doc /*
		 * allocations is the base feature of all AllocationUsages.
		 */
	}
}
