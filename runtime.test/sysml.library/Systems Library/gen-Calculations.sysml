standard library package Calculations{
	doc /*
	 * This package defines the base types for calculations and related behavioral elements in the
	 * SysML language.
	 */
	private import Performances::Evaluation;
	private import Performances::evaluations;
	private import Actions::Action;
	private import Actions::actions;
	abstract calc def Calculation : Action , Evaluation{
		doc /*
		 * Calculation is the most general class of evaluations of CalculationDefinitions in a
		 * system or part of a system. Calculation is the base class of all CalculationDefinitions.
		 */
		ref calc self : Calculation :>> Action::self :>> Evaluation::self;
		abstract calc subcalculations : Calculation :> calculations :> subactions{
			doc /*
			 * The subactions of this Calculation that are Calculations.
			 */
		}
	}
	abstract calc calculations [ 0 .. * ] nonunique : Calculation :> actions :> evaluations{
		doc /*
		 * calculations is the base Feature for all CalculationUsages.
		 */
	}
}
