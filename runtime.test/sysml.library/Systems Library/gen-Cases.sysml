standard library package Cases{
	doc /*
	 * This package defines the base types for cases and related behavioral elements 
	 * in the SysML language.
	 */
	private import Base::Anything;
	private import Requirements::RequirementCheck;
	private import Calculations::Calculation;
	private import Calculations::calculations;
	private import Parts::Part;
	private import Parts::parts;
	abstract case def Case : Calculation{
		doc /*
		 * Case is the most general class of performances of CaseDefinitions. 
		 * Case is the base class of all CaseDefinitions.
		 */
		ref case self : Case :>> Calculation::self;
		subject subj [ 1 ] : Anything{
			doc /*
			 * The subject that was investigated by this Case.
			 */
		}
		ref part actors [ 0 .. * ] : Part :> parts{
			doc /*
			 * The Parts that fill the role of actors for this Case.
			 * (Note: This is not itself an actor parameter, because specific actor
			 * parameters will be added for specific Cases.)
			 */
		}
		objective obj [ 1 ] : RequirementCheck{
			doc /*
			 * A check of whether the objective RequirementUsage was satisfied for this Case.
			 */
			subject subj default Case::result;
		}
		return ref result [ 0 .. * ]{
			doc /*
			 * The result determined by the case, which should satisfy the case objective.
			 */
		}
		abstract case subcases [ 0 .. * ] : Case :> cases :> subcalculations{
			doc /*
			 * Other Cases carried out as part of the performance of this Case.
			 */
		}
	}
	abstract case cases [ 0 .. * ] nonunique : Case :> calculations{
		doc /*
		 * cases is the base Feature of all CaseUsages.
		 */
	}
}
