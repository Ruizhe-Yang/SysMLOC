standard library package Parts{
	doc /*
 * This package defines the base types for parts and related structural elements in the
 * SysML language.
 */
	private import Objects::Object;
	private import Objects::objects;
	private import Items::Item;
	private import Items::items;
	private import Ports::Port;
	private import Ports::ports;
	private import Actions::Action;
	private import Actions::actions;
	private import States::StateAction;
	private import States::stateActions;
	abstract part def Part : Item{
		doc /*
		 * Part is the most general class of objects that represent all or a part of a system.
		 * Part is the base type of all PartDefinitions.
		 */
		ref self : Part :>> Item::self;
		part start : Part :>> Item::start;
		part done : Part :>> Item::done;
		abstract port ownedPorts [ 0 .. * ] : Port :> ports :> timeEnclosedOccurrences{
			doc /*
			 * Ports that are owned by this Part.
			 */
		}
		abstract ref action performedActions [ 0 .. * ] : Action :> actions :> enactedPerformances{
			doc /*
			 * Actions that are performed by this Part.
			 */
		}
		abstract action ownedActions [ 0 .. * ] : Action :> actions :> ownedPerformances{
			doc /*
			 * Actions that are owned by this Part.
			 */
			ref part this : Part :>> Action::this :>> ownedPerformances::this = that as Part{
				doc /*
				 * The "this" reference of an ownedAction is always its owning Part.
				 */
			}
		}
		abstract ref state exhibitedStates [ 0 .. * ] : StateAction :> stateActions :> performedActions{
			doc /*
			 * StateActions that are exhibited by this Part.
			 */
		}
		abstract state ownedStates [ 0 .. * ] : StateAction :> stateActions :> ownedActions{
			doc /*
			 * StateActions that are owned by this Part.
			 */
		}
	}
	abstract part parts [ 0 .. * ] nonunique : Part :> items{
		doc /*
		 * parts is the base feature of all part properties.
		 */
	}
}
