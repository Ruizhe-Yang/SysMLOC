standard library package UseCases{
	doc /*
	 * This package defines the base types for use cases and related behavioral elements in the SysML language.
	 */
	private import Cases::Case;
	private import Cases::cases;
	use case def UseCase : Case{
		doc /*
		 * UseCase is the most general class of performances of UseCaseDefinitions. 
		 * UseCase is the base class of all UseCaseDefinitions.
		 */
		ref use case self : UseCase :>> Case::self;
		subject subj :>> Case::subj;
		objective obj :>> Case::obj;
		ref use case start : UseCase :>> start{
			doc /*
			 * The starting snapshot of a Use Case. 
			 */
		}
		ref use case done : UseCase :>> done{
			doc /*
			 * The ending snapshot of a Use Case.
			 */
		}
		abstract use case subUseCases [ 0 .. * ] : UseCase :> useCases :> subcases{
			doc /*
			 * Other UseCases carried out as part of the performance of this UseCase.
			 */
		}
		abstract ref use case includedUseCases [ 0 .. * ] : UseCase :> useCases :> enclosedPerformances{
			doc /*
			 * Other UseCases included by this UseCase (i.e., as modeled by an 
			 * IncludeUseCaseUsage).
			 */
		}
	}
	use case useCases [ 0 .. * ] nonunique : UseCase :> cases{
		doc /*
		 * useCases is the base feature of all UseCaseUsages.
		 */
	}
}
