package 'Binding Connectors Example-2'{
	private import 'Port Example' :: *;
	part def Vehicle;
	part def FuelPump;
	part def FuelTank;
	part vehicle : Vehicle{
		part tank : FuelTankAssembly{
			port :>> fuelTankPort{
				out item :>> fuelSupply;
				in item :>> fuelReturn;
			}
			part pump : FuelPump{
				out item pumpOut : Fuel = fuelTankPort.fuelSupply;
				in item pumpIn : Fuel;
			}
			part tank : FuelTank{
				out item fuelOut : Fuel;
				in item fuelIn : Fuel = fuelTankPort.fuelReturn;
			}
		}
	}
}
