package 'Action Definition Example'{
	item def Scene;
	item def Image;
	item def Picture;
	action def Focus{
		in scene : Scene;
		out image : Image;
	}
	action def Shoot{
		in image : Image;
		out picture : Picture;
	}
	action def TakePicture{
		in scene : Scene;
		out picture : Picture;
		bind focus.scene = scene;
		action focus : Focus{
			in scene;
			out image;
		}
		flow focus.image to shoot.image;
		action shoot : Shoot{
			in image;
			out picture;
		}
		bind shoot.picture = picture;
	}
}
