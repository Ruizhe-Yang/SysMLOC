package 'Terminate Actions Example-2'{
	action def WorkflowProcess;
	part def Processor{
		ref action workflowProcess : WorkflowProcess;
		action internalProcess{
			// ...
		}
	}
	action terminateProcessing{
		in processor : Processor;
		terminate processor.workflowProcess{
		}
		terminate processor{
		}
	}
}
