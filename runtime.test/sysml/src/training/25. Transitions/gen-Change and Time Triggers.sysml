package 'Change and Time Triggers'{
	private import ISQ::TemperatureValue;
	private import ISQ::DurationValue;
	private import Time::TimeInstantValue;
	private import SI::h;
	attribute def OverTemp;
	part def Vehicle{
		attribute maintenanceTime : TimeInstantValue;
		attribute maintenanceInterval : DurationValue;
		attribute maxTemperature : TemperatureValue;
	}
	part def VehicleController;
	action senseTemperature{
		out temp : TemperatureValue;
	}
	state healthStates{
		in vehicle : Vehicle;
		in controller : VehicleController;
		entry;
		then normal;
		do senseTemperature;
		state normal;
		accept at vehicle.maintenanceTime then maintenance;
		accept when senseTemperature.temp > vehicle.maxTemperature do send new OverTemp() to controller then degraded;
		state maintenance{
			entry assign vehicle.maintenanceTime := vehicle.maintenanceTime + vehicle.maintenanceInterval;
		}
		accept after 48 [h] then normal;
		state degraded;
		accept when senseTemperature.temp <= vehicle.maxTemperature then normal;
	}
}
