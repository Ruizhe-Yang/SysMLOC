package 'Individuals and Roles'{
	private import 'Part Definition Example' :: *;
	part def Wheel;
	individual part def Vehicle_1 : Vehicle{
		part leftFrontWheel : Wheel;
		part rightFrontWheel : Wheel;
	}
	individual part def Wheel_1 : Wheel;
	individual part vehicle_1 : Vehicle_1{
		snapshot part vehicle_1_t0{
			snapshot leftFrontWheel_t0 : Wheel_1 :>> leftFrontWheel;
		}
		then snapshot part vehicle_1_t1{
			snapshot rightFrontWheel_t1 : Wheel_1 :>> rightFrontWheel;
		}
	}
}
