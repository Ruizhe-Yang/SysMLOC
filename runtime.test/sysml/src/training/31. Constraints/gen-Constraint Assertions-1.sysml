package 'Constraint Assertions-1'{
	private import ISQ :: *;
	private import SI :: *;
	private import NumericalFunctions :: *;
	part def Engine;
	part def Transmission;
	constraint def MassConstraint{
		in partMasses [ 0 .. * ] : MassValue;
		in massLimit : MassValue;
		sum(partMasses) <= massLimit
	}
	part def Vehicle{
		assert constraint massConstraint : MassConstraint{
			in partMasses = (chassisMass, engine.mass, transmission.mass);
			in massLimit = 2500[kg];
		}
		attribute chassisMass : MassValue;
		part engine : Engine{
			attribute mass : MassValue;
		}
		part transmission : Engine{
			attribute mass : MassValue;
		}
	}
}
