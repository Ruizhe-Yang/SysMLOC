package 'Use Case Usage Example'{
	private import 'Use Case Definition Example' :: *;
	part def 'Fuel Station';
	use case 'provide transportation' : 'Provide Transportation'{
		subject vehicle;
		first start;
		then include use case 'enter vehicle' : 'Enter Vehicle'{
			subject vehicle;
			actor :>> driver = 'provide transportation'::driver;
			actor :>> passengers = 'provide transportation'::passengers;
		}
		then use case 'drive vehicle'{
			subject vehicle;
			actor driver = 'provide transportation'::driver;
			actor environment = 'provide transportation'::environment;
			include 'add fuel' [ 0 .. * ]{
				subject vehicle;
				actor :>> fueler = driver;
			}
		}
		then include use case 'exit vehicle' : 'Exit Vehicle'{
			subject vehicle;
			actor :>> driver = 'provide transportation'::driver;
			actor :>> passengers = 'provide transportation'::passengers;
		}
		then done;
	}
	use case 'add fuel'{
		subject vehicle : Vehicle;
		actor fueler : Person;
		actor 'fuel station' : 'Fuel Station';
	}
}
