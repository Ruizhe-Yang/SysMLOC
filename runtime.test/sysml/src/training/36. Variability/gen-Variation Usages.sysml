package 'Variation Usages'{
	private import 'Variation Definitions' :: *;
	part def Vehicle;
	part def Transmission;
	part manualTransmission;
	part automaticTransmission;
	abstract part vehicleFamily : Vehicle{
		part engine [ 1 ] : EngineChoices;
		variation part transmission [ 1 ] : Transmission{
			variant manualTransmission;
			variant automaticTransmission;
		}
		assert constraint{
			(engine == engine::'4cylEngine' and transmission == transmission::manualTransmission ) xor (engine == engine::'6cylEngine' and transmission == transmission::automaticTransmission )
		}
	}
}
