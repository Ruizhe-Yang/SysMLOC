package 'Action Performance Example'{
	private import 'Action Decomposition' :: *;
	part def Camera;
	part def AutoFocus;
	part def Imager;
	part camera : Camera{
		perform action takePhoto [ * ordered takePicture part f : AutoFocus{
			perform takePhoto.focus;
		}
		part i : Imager{
			perform takePhoto.shoot;
		}
	}
}
