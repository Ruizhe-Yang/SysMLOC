package 'Local Clock Example'{
	private import ScalarValues::String;
	item def Start;
	item def Request;
	part def Server{
		part :>> localClock = Time::Clock();
		attribute today : String;
		port requestPort;
		state ServerBehavior{
			entry;
			then off;
			state off;
			accept Start via requestPort then waiting;
			state waiting;
			accept request : Request requestPort then responding;
			accept at Time::Iso8601DateTime(today + "11:59:00") then off;
			state responding;
			accept after 5 [SI::min] then waiting;
		}
	}
}
