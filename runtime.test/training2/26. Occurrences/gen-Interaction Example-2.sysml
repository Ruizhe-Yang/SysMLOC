package 'Interaction Example-2'{
	private import 'Event Occurrence Example' :: *;
	item def SetSpeed;
	item def SensedSpeed;
	item def FuelCommand;
	occurrence def CruiseControlInteraction{
		ref part driver : Driver{
			event setSpeedMessage.sourceEvent;
		}
		ref part vehicle : Vehicle{
			part cruiseController : CruiseController{
				event setSpeedMessage.targetEvent;
				then event sensedSpeedMessage.targetEvent;
				then event fuelCommandMessage.sourceEvent;
			}
			part speedometer : Speedometer{
				event sensedSpeedMessage.sourceEvent;
			}
			part engine : Engine{
				event fuelCommandMessage.targetEvent;
			}
		}
		message setSpeedMessage of SetSpeed;
		then message sensedSpeedMessage of SensedSpeed;
		message fuelCommandMessage of FuelCommand;
	}
}
