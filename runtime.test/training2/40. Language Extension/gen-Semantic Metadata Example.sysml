library package 'Semantic Metadata Example'{
	private import 'Model Library Example' :: *;
	private import Metaobjects::SemanticMetadata;
	metadata def situation : SemanticMetadata{
		:>> baseType = situations meta SysML::Usage;
	}
	metadata def cause : SemanticMetadata{
		:>> baseType = causes meta SysML::Usage;
	}
	metadata def failure : SemanticMetadata{
		:>> baseType = failures meta SysML::Usage;
	}
	metadata def causation : SemanticMetadata{
		:>> baseType = causations meta SysML::Usage;
	}
	metadata def scenario : SemanticMetadata{
		:>> baseType = scenarios meta SysML::Usage;
	}
}
