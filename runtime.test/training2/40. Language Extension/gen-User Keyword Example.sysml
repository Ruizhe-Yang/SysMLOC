package 'User Keyword Example'{
	private import ScalarValues::Real;
	private import 'Semantic Metadata Example' :: *;
	private import RiskMetadata::LevelEnum;
	part def Device{
		part battery{
			attribute power : Real;
		}
	}
	#scenario def DeviceFailure{
		ref device : Device;
		attribute minPower : Real;
		#cause 'battery old'{
			:>> probability = 0.01;
		}
		#causation first 'battery old' then 'power low';
		#situation 'power low'{
			constraint{
				device.battery.power < minPower
			}
		}
		#causation first 'power low' then 'device shutoff';
		#failure 'device shutoff'{
			:>> severity = LevelEnum::high;
		}
	}
}
